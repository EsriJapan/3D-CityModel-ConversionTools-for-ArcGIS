FME workspace tran_import_tokyo23_55cities_v112.fmw

Parameters:
- SourceDataset_CITYGML =   # Input CityGML File(s)
- TEMPLATEFILE_GEODATABASE_FILE =   # Template XML Workspace Document (Schema Only)
- DestDataset_GEODATABASE_FILE =   # Ouput File Geodatabase
- ADE_XSD_DOC_CITYGML =   # Additional ADE Schema File( iur1.4-schemas-uro-1.4-urbanObject.xsd )

Readers:
- CITYGML_1: CITYGML from $(SourceDataset_CITYGML)

Writers:
- GEODATABASE_FILE_1: GEODATABASE_FILE to $(DestDataset_GEODATABASE_FILE)

Note: CityGML Reader Parameters / GML SRS Axis Order: 2,1,3
Note: リスト属性はインデックス「0」を指定して抽出
AttributeCreator
    ATTR_TABLE:
      SET_TO tran_function = @Value(citygml_function{0})
      SET_TO tran_usage = @Value(citygml_usage{0})
      SET_TO uro_width = @Value(uro_width{0})
      SET_TO uro_widthType = @Value(uro_width_type{0})
      SET_TO uro_weekday12hourTrafficVolume = @Value(uro_traffic_volume{0}.uro_traffic_volume_uro_weekday12hour_traffic_volume)
      SET_TO uro_weekday24hourTrafficVolume = @Value(uro_traffic_volume{0}.uro_traffic_volume_uro_weekday24hour_traffic_volume)
      SET_TO uro_largeVehicleRate = @Value(uro_traffic_volume{0}.uro_traffic_volume_uro_large_vehicle_rate)
      SET_TO uro_congestionRate = @Value(uro_traffic_volume{0}.uro_traffic_volume_uro_congestion_rate)
      SET_TO uro_averageTravelSpeedInCongestion = @Value(uro_traffic_volume{0}.uro_traffic_volume_uro_average_travel_speed_in_congestion)
      SET_TO uro_observationPointName = @Value(uro_traffic_volume{0}.uro_traffic_volume_uro_observation_point_name)
      SET_TO uro_reference = @Value(uro_traffic_volume{0}.uro_traffic_volume_uro_reference)
      SET_TO uro_note = @Value(uro_traffic_volume{0}.uro_traffic_volume_uro_note)
      SET_TO uro_surveyYear = @Value(uro_traffic_volume{0}.uro_traffic_volume_uro_survey_year)
    -> AttributeManager
AttributeManager
    ATTR_TABLE:
      RENAME_SET_VALUE gml_id > tran_Road_gml_id
      REMOVE gml_parent_id
      REMOVE citygml_target_uri
      REMOVE citygml_feature_role
      REMOVE citygml_feature_role_attr_name
      REMOVE citygml_feature_role_attr_val
      REMOVE gml_description
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_class
      REMOVE citygml_class_codeSpace
      REMOVE citygml_function{}
      REMOVE citygml_function{}.codeSpace
      REMOVE citygml_usage{}
      REMOVE citygml_usage{}.codeSpace
      REMOVE citygml_traffic_area{}.xlink_href
      REMOVE citygml_auxiliary_traffic_area{}.xlink_href
      REMOVE citygml_level_of_detail{}
      REMOVE uro_traffic_volume{}.uro_traffic_volume_uro_weekday12hour_traffic_volume
      REMOVE uro_traffic_volume{}.uro_traffic_volume_uro_weekday24hour_traffic_volume
      REMOVE uro_traffic_volume{}.uro_traffic_volume_uro_large_vehicle_rate
      REMOVE uro_traffic_volume{}.uro_traffic_volume_uro_congestion_rate
      REMOVE uro_traffic_volume{}.uro_traffic_volume_uro_average_travel_speed_in_congestion
      REMOVE uro_traffic_volume{}.uro_traffic_volume_uro_observation_point_name
      REMOVE uro_traffic_volume{}.uro_traffic_volume_uro_urban_plan_type
      REMOVE uro_traffic_volume{}.uro_traffic_volume_uro_urban_plan_type_codeSpace
      REMOVE uro_traffic_volume{}.uro_traffic_volume_uro_area_classification_type
      REMOVE uro_traffic_volume{}.uro_traffic_volume_uro_area_classification_type_codeSpace
      REMOVE uro_traffic_volume{}.uro_traffic_volume_uro_prefecture
      REMOVE uro_traffic_volume{}.uro_traffic_volume_uro_prefecture_codeSpace
      REMOVE uro_traffic_volume{}.uro_traffic_volume_uro_city
      REMOVE uro_traffic_volume{}.uro_traffic_volume_uro_city_codeSpace
      REMOVE uro_traffic_volume{}.uro_traffic_volume_uro_reference
      REMOVE uro_traffic_volume{}.uro_traffic_volume_uro_note
      REMOVE uro_traffic_volume{}.uro_traffic_volume_uro_survey_year
      REMOVE uro_width{}
      REMOVE uro_width{}.units
      REMOVE uro_width_type{}
      REMOVE uro_width_type{}.codeSpace
    -> GeometryPartExtractor
GeometryPartExtractor
    GQUERY:
      for $geom in //geometry
      where $geom/parent::geometry/@fme_geometry_type = 'IFMEFace'
      return number($geom/@fme_id)
    EXTRACTED -> lod1_Road (writer GEODATABASE_FILE_1)

Bookmark: CityGML Feature Types
CityModel (reader CITYGML_1)
    attributes: citygml_target_uri xml_buffer, gml_description xml_buffer, gml_name xml_buffer, citygml_city_object_member{}.xlink_href xml_buffer, gml_feature_member{}.xlink_href xml_buffer
Road (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, uro_traffic_volume{}.uro_traffic_volume_uro_weekday12hour_traffic_volume xml_int64, uro_traffic_volume{}.uro_traffic_volume_uro_weekday24hour_traffic_volume xml_int64, uro_traffic_volume{}.uro_traffic_volume_uro_large_vehicle_rate xml_real64, uro_traffic_volume{}.uro_traffic_volume_uro_congestion_rate xml_real64, uro_traffic_volume{}.uro_traffic_volume_uro_average_travel_speed_in_congestion xml_real64, uro_traffic_volume{}.uro_traffic_volume_uro_observation_point_name xml_buffer, uro_traffic_volume{}.uro_traffic_volume_uro_urban_plan_type xml_buffer,
      uro_traffic_volume{}.uro_traffic_volume_uro_urban_plan_type_codeSpace xml_buffer, uro_traffic_volume{}.uro_traffic_volume_uro_area_classification_type xml_buffer, uro_traffic_volume{}.uro_traffic_volume_uro_area_classification_type_codeSpace xml_buffer, uro_traffic_volume{}.uro_traffic_volume_uro_prefecture xml_buffer, uro_traffic_volume{}.uro_traffic_volume_uro_prefecture_codeSpace xml_buffer, uro_traffic_volume{}.uro_traffic_volume_uro_city xml_buffer, uro_traffic_volume{}.uro_traffic_volume_uro_city_codeSpace xml_buffer, uro_traffic_volume{}.uro_traffic_volume_uro_reference xml_buffer, uro_traffic_volume{}.uro_traffic_volume_uro_note xml_buffer, uro_traffic_volume{}.uro_traffic_volume_uro_survey_year xml_buffer, uro_width{} xml_real64, uro_width{}.units xml_buffer, uro_width_type{} xml_buffer, uro_width_type{}.codeSpace xml_buffer
    -> AttributeCreator

Bookmark: GDBに書込み（XMLスキーマを指定）
lod1_Road (writer GEODATABASE_FILE_1)
    attributes: tran_Road_gml_id char(50), gml_name char(50), tran_function char(10), tran_usage char(10), uro_width double, uro_widthType char(10), uro_weekday12hourTrafficVolume integer, uro_weekday24hourTrafficVolume integer, uro_largeVehicleRate double, uro_congestionRate double, uro_averageTravelSpeedInCongestion double, uro_observationPointName char(50), uro_reference char(50), uro_note char(50), uro_surveyYear char(50)
