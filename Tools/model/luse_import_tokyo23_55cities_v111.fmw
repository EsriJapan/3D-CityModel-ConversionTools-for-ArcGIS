FME workspace luse_import_tokyo23_55cities_v111.fmw

Parameters:
- SourceDataset_CITYGML =   # Input CityGML File(s)
- TEMPLATEFILE_GEODATABASE_FILE =   # Template XML Workspace Document (Schema Only)
- DestDataset_GEODATABASE_FILE =   # Output File Geodatabase

Readers:
- CITYGML_1: CITYGML from $(SourceDataset_CITYGML)
- TEXTLINE_1: TEXTLINE from $(SourceDataset_CITYGML)

Writers:
- GEODATABASE_FILE_1: GEODATABASE_FILE to $(DestDataset_GEODATABASE_FILE)

Note: CityGML Reader Parameters / GML SRS Axis Order: 2,1,3
AttributeCreator
    ATTR_TABLE:
      SET_TO uro_nominalArea = @Value(uro_nominal_area{0})
      SET_TO uro_ownerType = @Value(uro_owner_type{0})
      SET_TO uro_owner = @Value(uro_owner{0})
      SET_TO uro_areaInSquareMeter = @Value(uro_area_in_square_meter{0})
      SET_TO uro_areaInHa = @Value(uro_area_in_ha{0})
      SET_TO uro_urbanPlanType = @Value(uro_urban_plan_type{0})
      SET_TO uro_districtsAndZonesType = @Value(uro_districts_and_zones_type{0})
      SET_TO uro_areaClassificationType = @Value(uro_area_classification_type{0})
      SET_TO uro_prefecture = @Value(uro_prefecture{0})
      SET_TO uro_city = @Value(uro_city{0})
      SET_TO uro_surveyYear = @Value(uro_survey_year{0})
    -> FeatureJoiner [LEFT]
Note: FeatureJoiner [FeatureJoiner] / Transformer: / Group By Mode: Process At End (Blocking) / Join Mode: / Join Mode: Left / Attribute Conflict Resolution: Use Left / Geometry Handling: Use Left / Join On: LeftRightComparison Modegml_idlanduse_idAutomatic
FeatureJoiner
    ATTR_CONFLICT_RES = Use Left
    GEOMETRY_HANDLING = Use Left
    JOIN_KEYS = gml_id landuse_id AUTO
    JOIN_MODE = Left
    JOINED -> AttributeManager
AttributeManager
    ATTR_TABLE:
      RENAME_SET_VALUE gml_id > luse_LandUse_gml_id
      RENAME_SET_VALUE citygml_class > luse_class
      REMOVE gml_parent_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_class_codeSpace
      REMOVE citygml_function{}
      REMOVE citygml_function{}.codeSpace
      REMOVE citygml_usage{}
      REMOVE citygml_usage{}.codeSpace
      REMOVE citygml_level_of_detail{}
      REMOVE uro_area_classification_type{}
      REMOVE uro_area_classification_type{}.codeSpace
      REMOVE uro_area_in_ha{}
      REMOVE uro_area_in_ha{}.units
      REMOVE uro_area_in_square_meter{}
      REMOVE uro_area_in_square_meter{}.units
      REMOVE uro_city{}
      REMOVE uro_city{}.codeSpace
      REMOVE uro_districts_and_zones_type{}
      REMOVE uro_districts_and_zones_type{}.codeSpace
      REMOVE uro_land_use_plan_type{}
      REMOVE uro_land_use_plan_type{}.codeSpace
      REMOVE uro_nominal_area{}
      REMOVE uro_nominal_area{}.units
      REMOVE uro_note{}
      REMOVE uro_owner{}
      REMOVE uro_owner_type{}
      REMOVE uro_owner_type{}.codeSpace
      REMOVE uro_prefecture{}
      REMOVE uro_prefecture{}.codeSpace
      REMOVE uro_reference{}
      REMOVE uro_survey_year{}
      REMOVE uro_urban_plan_type{}
      REMOVE uro_urban_plan_type{}.codeSpace
      REMOVE FID
      REMOVE landuse_id
    -> GeometryPartExtractor
GeometryPartExtractor
    GQUERY:
      for $geom in //geometry
      where $geom/parent::geometry/@fme_geometry_type = 'IFMEFace'
      return number($geom/@fme_id)
    EXTRACTED -> lod1_LandUse (writer GEODATABASE_FILE_1)

Bookmark: CityGML Feature Types
CityModel (reader CITYGML_1)
    attributes: citygml_target_uri xml_buffer, gml_description xml_buffer, gml_name xml_buffer, citygml_city_object_member{}.xlink_href xml_buffer, gml_feature_member{}.xlink_href xml_buffer
LandUse (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_level_of_detail{} xml_buffer, uro_area_classification_type{} xml_buffer, uro_area_classification_type{}.codeSpace xml_buffer, uro_area_in_ha{} xml_real64, uro_area_in_ha{}.units xml_buffer, uro_area_in_square_meter{} xml_real64, uro_area_in_square_meter{}.units xml_buffer, uro_city{} xml_buffer, uro_city{}.codeSpace xml_buffer, uro_districts_and_zones_type{} xml_buffer,
      uro_districts_and_zones_type{}.codeSpace xml_buffer, uro_land_use_plan_type{} xml_buffer, uro_land_use_plan_type{}.codeSpace xml_buffer, uro_nominal_area{} xml_real64, uro_nominal_area{}.units xml_buffer, uro_note{} xml_buffer, uro_owner{} xml_buffer, uro_owner_type{} xml_buffer, uro_owner_type{}.codeSpace xml_buffer, uro_prefecture{} xml_buffer, uro_prefecture{}.codeSpace xml_buffer, uro_reference{} xml_buffer, uro_survey_year{} xml_buffer, uro_urban_plan_type{} xml_buffer, uro_urban_plan_type{}.codeSpace xml_buffer, FID xml_buffer
    -> AttributeCreator

Bookmark: 汎用属性セットの XML を作成
text_line (reader TEXTLINE_1)
    attributes: text_line_data buffer
    -> Sampler
Sampler
    RATE = 1
    SAMPLE_MODE = No
    SAMPLE_TYPE_LONG = First N Features
    SAMPLED -> XMLTemplater [ROOT]
    SAMPLED -> XMLTemplater [SUB]
    NOT_SAMPLED -> XMLTemplater [SUB]
Note: XMLTemplaterで作成するXML / ---------- / <?xml version="1.0" encoding="UTF-16"?> / </root> / <LandUse gml_id="PRK_1f71c6cb-0d1b-4468-9d75-a24cd4fe738b"> / <attr name="gen_大字_町コード" type="TEXT">大字・町コード</attr> / <attr name="gen_町_丁目コード" type="TEXT">町・丁目コード</attr> / <attr name="gen_13_区市町村コード_大字_町コード_町_丁目コード" type="TEXT">13+区市町村コード+大字・町コード+町・丁目コード</attr> / <attr name="gen_区市町村名称" type="TEXT">区市町村名称</attr> / <attr name="gen_町丁目名称" type="TEXT">町丁目名称</attr> / <attr name="gen_土地利用区分_都道府県区分_" type="TEXT">1110</attr> / <attr name="gen_変化フラグ" type="TEXT">1</attr> / <attr name="gen_過年度修正フラグ" type="TEXT">1</attr> / </LandUse> / (中略) / </root>
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace luse="http://www.opengis.net/citygml/landuse/2.0";

      {
      let $doc := fme:get-xml-attribute("text_line_data")
      for $l in $doc//luse:LandUse
      return
      <LandUse gml_id="{data($l/@gml:id)}">{
          for $genStrAttr in $l/gen:stringAttribute
          where $l/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $l/gen:intAttribute
          where $l/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $l/gen:doubleAttribute
          where $l/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $l/gen:dateAttribute
          where $l/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $l/gen:uriAttribute
          where $l/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $l/gen:measureAttribute
          where $l/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $l/gen:genericAttributeSet
          where $attrSet/gen:measureAttribute
              for $measureAttr in $attrSet/gen:measureAttribute[@name eq "code"]
              let $mtempname := "gen_"||{data($attrSet/@name)}
              let $mname := fn:translate($mtempname, "・（(- 「」、。－+＋）)", "____________")
              let $mtype := "DOUBLE"
              return
              <attr name="{$mname}" type="{$mtype}">{data($measureAttr/gen:value)}</attr>
          }{
          for $attrSet in $l/gen:genericAttributeSet
          where $attrSet/gen:intAttribute
              for $intAttr in $attrSet/gen:intAttribute[@name eq "code"]
              let $itempname := "gen_"||{data($attrSet/@name)}
              let $iname := fn:translate($itempname, "・（(- 「」、。－+＋）)", "____________")
              let $itype := "LONG"
              return
              <attr name="{$iname}" type="{$itype}">{data($intAttr/gen:value)}</attr>
          }{
          for $attrSet in $l/gen:genericAttributeSet
          where $attrSet/gen:stringAttribute
              for $stringAttr in $attrSet/gen:stringAttribute[@name eq "code"]
              let $stempname := "gen_"||{data($attrSet/@name)}
              let $sname := fn:translate($stempname, "・（(- 「」、。－+＋）)", "____________")
              let $stype := "TEXT"
              return
              <attr name="{$sname}" type="{$stype}">{data($stringAttr/gen:value)}</attr>
          }{
          for $attrSet in $l/gen:genericAttributeSet
          where $attrSet/gen:doubleAttribute
              for $doubleAttr in $attrSet/gen:doubleAttribute[@name eq "code"]
              let $dtempname := "gen_"||{data($attrSet/@name)}
              let $dname := fn:translate($dtempname, "・（(- 「」、。－+＋）)", "____________")
              let $dtype := "DOUBLE"
              return
              <attr name="{$dname}" type="{$dtype}">{data($doubleAttr/gen:value)}</attr>
          }{
          for $attrSet in $l/gen:genericAttributeSet
          where $attrSet/gen:dateAttribute
              for $dateAttr in $attrSet/gen:dateAttribute[@name eq "code"]
              let $datetempname := "gen_"||{data($attrSet/@name)}
              let $datename := fn:translate($datetempname, "・（(- 「」、。－+＋）)", "____________")
              let $datetype := "TEXT"
              return
              <attr name="{$datename}" type="{$datetype}">{data($dateAttr/gen:value)}</attr>
          }{
          for $attrSet in $l/gen:genericAttributeSet
          where $attrSet/gen:uriAttribute
              for $uriAttr in $attrSet/gen:uriAttribute[@name eq "code"]
              let $utempname := "gen_"||{data($attrSet/@name)}
              let $uname := fn:translate($utempname, "・（(- 「」、。－+＋）)", "____________")
              let $utype := "TEXT"
              return
              <attr name="{$uname}" type="{$utype}">{data($uriAttr/gen:value)}</attr>
          }</LandUse>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = Yes
    OUTPUT_ENCODING = utf-8
    REMOVE_ALL_COMMENT = No
    REMOVE_EMPTY_ELEMENT = No
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    KEEP_ATTRS = _result
    -> XMLFragmenter
Note: 図形ごとに、汎用属性のXMLを作成
XMLFragmenter
    ATTRIBUTE_XML = _result
    EMBEDDED_EXPRESSIONS = root/LandUse
    FEATURE_TYPES_FORMAT_NAME = XML
    MERGE_ATTRS = No
    REJECT_FEATURES_WITH_NO_FRAGMENTS = YES
    XML_SOURCE_TYPE = Attribute with XML document
    FRAGMENTS -> XMLXQueryExtractor_2
Note: Joinするときにキーとして使用するgml_idを属性として格納
XMLXQueryExtractor_2
    NEW_ATTRIBUTES = landuse_id
    QUERY_EXPR:
      declare namespace gml="http://www.opengis.net/gml";
      declare namespace gen="http://www.opengis.net/citygml/generics/2.0";
      declare namespace luse="http://www.opengis.net/citygml/landuse/2.0";

      fme:set-attribute('landuse_id', data(/LandUse/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager_2
AttributeManager_2
    ATTR_TABLE:
      RENAME_SET_VALUE xml_fragment > xml_genericAttributeSet
      REMOVE xml_id
      REMOVE xml_matched_element
      REMOVE xml_parent_id
      REMOVE xml_parent_child_pos
      REMOVE _result
    -> FeatureJoiner [RIGHT]

Bookmark: GDBに書込み(XMLスキーマを指定)
lod1_LandUse (writer GEODATABASE_FILE_1)
    attributes: luse_LandUse_gml_id char(50), luse_class char(10), uro_nominalArea double, uro_ownerType char(50), uro_owner char(50), uro_areaInSquareMeter double, uro_areaInHa double, uro_urbanPlanType char(10), uro_districtsAndZonesType char(10), uro_areaClassificationType char(10), uro_prefecture char(2), uro_city char(5), uro_surveyYear char(50), xml_genericAttributeSet char(10000)
