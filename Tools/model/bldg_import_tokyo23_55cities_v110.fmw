FME workspace bldg_import_tokyo23_55cities_v110.fmw

Parameters:
- SourceDataset_CITYGML =   # Input CityGML File(s)
- TEMPLATEFILE_GEODATABASE_FILE =   # Template XML Workspace Document (Schema Only)
- DestDataset_GEODATABASE_FILE =   # Output File Geodatabase

Readers:
- CITYGML_1: CITYGML from $(SourceDataset_CITYGML)
- TEXTLINE_1: TEXTLINE from $(SourceDataset_CITYGML)
- GEODATABASE_XML_1: GEODATABASE_XML from $(TEMPLATEFILE_GEODATABASE_FILE)
- XML_1: XML from $(SourceDataset_CITYGML)

Writers:
- GEODATABASE_FILE_1: GEODATABASE_FILE to $(DestDataset_GEODATABASE_FILE)

Note: CityGML Reader Parameters / GML SRS Axis Order: 2,1,3
Note: ・リスト属性はインデックス「0」を指定して抽出
AttributeCreator_2
    ATTR_TABLE = SET_TO bldg_function = @Value(citygml_function{0})
    -> AttributeManager_10
AttributeManager_10
    ATTR_TABLE:
      RENAME_SET_VALUE gml_id > bldg_BuildingInstallation_gml_id
      REMOVE citygml_target_uri
      REMOVE citygml_feature_role
      REMOVE citygml_feature_role_attr_name
      REMOVE citygml_feature_role_attr_val
      REMOVE gml_description
      RENAME_SET_VALUE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      RENAME_SET_VALUE citygml_class > bldg_class
      REMOVE citygml_class_codeSpace
      REMOVE citygml_function{}
      REMOVE citygml_function{}.codeSpace
      REMOVE citygml_usage{}
      REMOVE citygml_usage{}.codeSpace
      REMOVE citygml_bounded_by{}.xlink_href
      RENAME_SET_VALUE gml_parent_id > bldg_Building_gml_id
    -> lod2_BuildingInstallation (writer GEODATABASE_FILE_1)
AttributeManager_9
    ATTR_TABLE:
      RENAME_SET_VALUE gml_id > bldg_OuterFloorSurface_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      REMOVE citygml_opening{}.xlink_href
    -> lod2_OuterFloorSurface (writer GEODATABASE_FILE_1)
AttributeManager_8
    ATTR_TABLE:
      RENAME_SET_VALUE gml_id > bldg_ClosureSurface_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      REMOVE citygml_opening{}.xlink_href
    -> lod2_ClosureSurface (writer GEODATABASE_FILE_1)
AttributeManager_4
    ATTR_TABLE:
      RENAME_SET_VALUE gml_id > bldg_RoofSurface_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      REMOVE citygml_opening{}.xlink_href
    -> lod2_RoofSurface (writer GEODATABASE_FILE_1)
AttributeManager_5
    ATTR_TABLE:
      RENAME_SET_VALUE gml_id > bldg_WallSurface_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      REMOVE citygml_opening{}.xlink_href
    -> lod2_WallSurface (writer GEODATABASE_FILE_1)
AttributeManager_6
    ATTR_TABLE:
      RENAME_SET_VALUE gml_id > bldg_GroundSurface_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      REMOVE citygml_opening{}.xlink_href
    -> lod2_GroundSurface (writer GEODATABASE_FILE_1)
AttributeManager_7
    ATTR_TABLE:
      RENAME_SET_VALUE gml_id > bldg_OuterCeilingSurface_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE gml_name
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      REMOVE citygml_level_of_detail{}
      REMOVE citygml_opening{}.xlink_href
    -> lod2_OuterCeilingSurface (writer GEODATABASE_FILE_1)
Note: Mode: Flatten One Level (default)
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryPropertyExtractor_2
Note: Geometry XQuery: / This part | Hierarchy Position | Is | Root Node / Property to Extract: Geometry Name / Geometry Name Attribute: _geometry_name
GeometryPropertyExtractor_2
    EXTRACTTYPE_PARAM = Geometry Name
    GEOM_NAME_FIELD = _geometry_name
    GQUERY:
      for $geom in //geometry
      where $geom/count(parent::geometry) = 0
      return number($geom/@fme_id)
    EXTRACTED -> FeatureJoiner_4 [LEFT]
Note: Mode: Flatten One Level (default)
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryPropertyExtractor
Note: Geometry XQuery: / This part | Hierarchy Position | Is | Root Node / Property to Extract: Geometry Name / Geometry Name Attribute: _geometry_name
GeometryPropertyExtractor
    EXTRACTTYPE_PARAM = Geometry Name
    GEOM_NAME_FIELD = _geometry_name
    GQUERY:
      for $geom in //geometry
      where $geom/count(parent::geometry) = 0
      return number($geom/@fme_id)
    EXTRACTED -> FeatureJoiner [LEFT]
Note: XMLFlattener [XMLFlattener] / XML Source: / XML Source Type: Attribute with XML document / XML Attribute: citygml_address / Flatten Paths: / Elements to Match: xAL:Address / Customize Attributes: / Elements as XML Fragments: <not set> / Expose Attributes: / Attributes to Expose:
XMLFlattener
    ATTRIBUTE_XML = citygml_address
    EMBEDDED_EXPRESSIONS = xAL:Address
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeExposer
Note: AttributeExposer [AttributeExposer] / Attributes To Expose: Address
AttributeExposer
    ATTR_LIST = Address
    -> FeatureJoiner [RIGHT]
    -> FeatureJoiner_4 [RIGHT]
Note: FeatureJoiner_4 [FeatureJoiner] / Transformer: / Group By Mode: Process At End (Blocking) / Join Mode: / Join Mode: Left / Attribute Conflict Resolution: Use Left / Geometry Handling: Use Left / Join On: LeftRightComparison Modegml_idgml_parent_idAutomatic
FeatureJoiner_4
    ATTR_CONFLICT_RES = Use Left
    GEOMETRY_HANDLING = Use Left
    JOIN_KEYS = gml_id gml_parent_id AUTO
    JOIN_MODE = Left
    JOINED -> AttributeCreator_3
Note: FeatureJoiner [FeatureJoiner] / Transformer: / Group By Mode: Process At End (Blocking) / Join Mode: / Join Mode: Left / Attribute Conflict Resolution: Use Left / Geometry Handling: Use Left / Join On: LeftRightComparison Modegml_idgml_parent_idAutomatic
FeatureJoiner
    ATTR_CONFLICT_RES = Use Left
    GEOMETRY_HANDLING = Use Left
    JOIN_KEYS = gml_id gml_parent_id AUTO
    JOIN_MODE = Left
    JOINED -> AttributeCreator
Note: FeatureJoiner_2 [FeatureJoiner] / Transformer: / Group By Mode: Process At End (Blocking) / Join Mode: / Join Mode: Left / Attribute Conflict Resolution: Use Left / Geometry Handling: Use Left / Join On: LeftRightComparison Modebldg_Building_gml_idbuilding_idString
Note: 汎用属性のXMLを図形に結合
FeatureJoiner_2
    ATTR_CONFLICT_RES = Use Left
    GEOMETRY_HANDLING = Use Left
    JOIN_KEYS = bldg_Building_gml_id building_id STRING
    JOIN_MODE = Left
    JOINED -> FeatureJoiner_3 [LEFT]
Note: Test Condition / Output Port / If / @Value(_geometry_name) BEGINS_WITH lod1 / lod1_BuildingPart / Else If / @Value(_geometry_name) BEGINS_WITH lod2 / lod2_BuildingPart / Else / <All Other Conditions> / <Unfiltered>
TestFilter_2
    DEFAULT_VALUE = <UNFILTERED>
    TEST_LIST = "BOOL_OP,OR,COMPOSITE_TEST,""""""1"""""",TEST_CLAUSE,CASE_INSENSITIVE_TEST @Value(_geometry_name) BEGINS_WITH lod1",lod1_BuilingPart,"BOOL_OP,OR,COMPOSITE_TEST,""""""1"""""",TEST_CLAUSE,CASE_INSENSITIVE_TEST @Value(_geometry_name) BEGINS_WITH lod2",lod2_BuilingPart
    lod1_BuilingPart -> lod1_BuildingPart (writer GEODATABASE_FILE_1)
    lod2_BuilingPart -> lod2_BuildingPart (writer GEODATABASE_FILE_1)
Note: Test Condition / Output Port / If / @Value(_geometry_name) BEGINS_WITH lod0 / LOD0 / Else If / @Value(_geometry_name) BEGINS_WITH lod1 / LOD1 / Else If / @Value(_geometry_name) BEGINS_WITH lod2 / LOD2 / Else / <All Other Conditions> / <Unfiltered>
TestFilter
    DEFAULT_VALUE = <UNFILTERED>
    TEST_LIST = "BOOL_OP,OR,COMPOSITE_TEST,""""""1"""""",TEST_CLAUSE,CASE_INSENSITIVE_TEST @Value(_geometry_name) BEGINS_WITH lod0",LOD0,"BOOL_OP,OR,COMPOSITE_TEST,""""""1"""""",TEST_CLAUSE,CASE_INSENSITIVE_TEST @Value(_geometry_name) BEGINS_WITH lod1",LOD1,"BOOL_OP,OR,COMPOSITE_TEST,""""""1"""""",TEST_CLAUSE,CASE_INSENSITIVE_TEST @Value(_geometry_name) BEGINS_WITH lod2",LOD2
    LOD0 -> GeometryPartExtractor
    LOD1 -> lod1_Building (writer GEODATABASE_FILE_1)
    LOD2 -> lod2_Building (writer GEODATABASE_FILE_1)
GeometryPartExtractor
    GQUERY:
      for $geom in //geometry
      where $geom/parent::geometry/@fme_geometry_type = 'IFMEFace'
      return number($geom/@fme_id)
    EXTRACTED -> lod0_Building (writer GEODATABASE_FILE_1)

Bookmark: CityGML Feature Types
BuildingInstallation (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer
    -> AttributeCreator_2
OuterFloorSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> AttributeManager_9
ClosureSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> AttributeManager_8
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> AttributeManager_4
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> AttributeManager_5
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> AttributeManager_6
OuterCeilingSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> AttributeManager_7
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_details{}.uro_building_details_uro_serial_number_of_building_certification xml_buffer, uro_building_details{}.uro_building_details_uro_site_area xml_real64, uro_building_details{}.uro_building_details_uro_site_area_units xml_buffer, uro_building_details{}.uro_building_details_uro_building_footprint_area xml_real64, uro_building_details{}.uro_building_details_uro_building_footprint_area_units xml_buffer, uro_building_details{}.uro_building_details_uro_building_roof_edge_area xml_real64, uro_building_details{}.uro_building_details_uro_building_roof_edge_area_units xml_buffer, uro_building_details{}.uro_building_details_uro_development_area xml_real64, uro_building_details{}.uro_building_details_uro_development_area_units xml_buffer, uro_building_details{}.uro_building_details_uro_total_floor_area xml_real64, uro_building_details{}.uro_building_details_uro_total_floor_area_units xml_buffer, uro_building_details{}.uro_building_details_uro_building_structure_type xml_buffer, uro_building_details{}.uro_building_details_uro_building_structure_type_codeSpace xml_buffer, uro_building_details{}.uro_building_details_uro_fireproof_structure_type xml_buffer, uro_building_details{}.uro_building_details_uro_fireproof_structure_type_codeSpace xml_buffer, uro_building_details{}.uro_building_details_uro_implementing_body xml_buffer, uro_building_details{}.uro_building_details_uro_urban_plan_type xml_buffer, uro_building_details{}.uro_building_details_uro_urban_plan_type_codeSpace xml_buffer, uro_building_details{}.uro_building_details_uro_districts_and_zones_type xml_buffer, uro_building_details{}.uro_building_details_uro_districts_and_zones_type_codeSpace xml_buffer,
      uro_building_details{}.uro_building_details_uro_land_use_plan_type xml_buffer, uro_building_details{}.uro_building_details_uro_land_use_plan_type_codeSpace xml_buffer, uro_building_details{}.uro_building_details_uro_area_classification_type xml_buffer, uro_building_details{}.uro_building_details_uro_area_classification_type_codeSpace xml_buffer, uro_building_details{}.uro_building_details_uro_prefecture xml_buffer, uro_building_details{}.uro_building_details_uro_prefecture_codeSpace xml_buffer, uro_building_details{}.uro_building_details_uro_city xml_buffer, uro_building_details{}.uro_building_details_uro_city_codeSpace xml_buffer, uro_building_details{}.uro_building_details_uro_reference xml_buffer, uro_building_details{}.uro_building_details_uro_note xml_buffer, uro_building_details{}.uro_building_details_uro_survey_year xml_buffer, uro_extended_attribute{}.uro_key_value_pair_uro_key xml_buffer, uro_extended_attribute{}.uro_key_value_pair_uro_key_codeSpace xml_buffer, uro_extended_attribute{}.uro_key_value_pair_uro_string_value xml_buffer, uro_extended_attribute{}.uro_key_value_pair_uro_int_value xml_int64, uro_extended_attribute{}.uro_key_value_pair_uro_double_value xml_real64, uro_extended_attribute{}.uro_key_value_pair_uro_code_value xml_buffer, uro_extended_attribute{}.uro_key_value_pair_uro_code_value_codeSpace xml_buffer, uro_extended_attribute{}.uro_key_value_pair_uro_measured_value xml_real64, uro_extended_attribute{}.uro_key_value_pair_uro_measured_value_units xml_buffer, uro_extended_attribute{}.uro_key_value_pair_uro_date_value xml_date, uro_extended_attribute{}.uro_key_value_pair_uro_uri_value xml_buffer, uro_large_customer_facilities{}.uro_large_customer_facilities_uro_class xml_buffer, uro_large_customer_facilities{}.uro_large_customer_facilities_uro_class_codeSpace xml_buffer, uro_large_customer_facilities{}.uro_large_customer_facilities_uro_name xml_buffer, uro_large_customer_facilities{}.uro_large_customer_facilities_uro_capacity xml_int64, uro_large_customer_facilities{}.uro_large_customer_facilities_uro_owner xml_buffer, uro_large_customer_facilities{}.uro_large_customer_facilities_uro_total_floor_area xml_real64, uro_large_customer_facilities{}.uro_large_customer_facilities_uro_total_floor_area_units xml_buffer, uro_large_customer_facilities{}.uro_large_customer_facilities_uro_total_store_floor_area xml_real64,
      uro_large_customer_facilities{}.uro_large_customer_facilities_uro_total_store_floor_area_units xml_buffer, uro_large_customer_facilities{}.uro_large_customer_facilities_uro_inaugural_date xml_date, uro_large_customer_facilities{}.uro_large_customer_facilities_uro_key_tenants xml_buffer, uro_large_customer_facilities{}.uro_large_customer_facilities_uro_availability xml_boolean, uro_large_customer_facilities{}.uro_large_customer_facilities_uro_urban_plan_type xml_buffer, uro_large_customer_facilities{}.uro_large_customer_facilities_uro_urban_plan_type_codeSpace xml_buffer, uro_large_customer_facilities{}.uro_large_customer_facilities_uro_districts_and_zones_type xml_buffer, uro_large_customer_facilities{}.uro_large_customer_facilities_uro_districts_and_zones_type_codeSpace xml_buffer, uro_large_customer_facilities{}.uro_large_customer_facilities_uro_land_use_plan_type xml_buffer, uro_large_customer_facilities{}.uro_large_customer_facilities_uro_land_use_plan_type_codeSpace xml_buffer, uro_large_customer_facilities{}.uro_large_customer_facilities_uro_area_classification_type xml_buffer, uro_large_customer_facilities{}.uro_large_customer_facilities_uro_area_classification_type_codeSpace xml_buffer, uro_large_customer_facilities{}.uro_large_customer_facilities_uro_prefecture xml_buffer, uro_large_customer_facilities{}.uro_large_customer_facilities_uro_prefecture_codeSpace xml_buffer, uro_large_customer_facilities{}.uro_large_customer_facilities_uro_city xml_buffer, uro_large_customer_facilities{}.uro_large_customer_facilities_uro_city_codeSpace xml_buffer, uro_large_customer_facilities{}.uro_large_customer_facilities_uro_reference xml_buffer, uro_large_customer_facilities{}.uro_large_customer_facilities_uro_note xml_buffer, uro_large_customer_facilities{}.uro_large_customer_facilities_uro_survey_year xml_buffer
    -> Deaggregator_2
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_building_details{}.uro_building_details_uro_serial_number_of_building_certification xml_buffer, uro_building_details{}.uro_building_details_uro_site_area xml_real64, uro_building_details{}.uro_building_details_uro_site_area_units xml_buffer, uro_building_details{}.uro_building_details_uro_building_footprint_area xml_real64, uro_building_details{}.uro_building_details_uro_building_footprint_area_units xml_buffer, uro_building_details{}.uro_building_details_uro_building_roof_edge_area xml_real64, uro_building_details{}.uro_building_details_uro_building_roof_edge_area_units xml_buffer, uro_building_details{}.uro_building_details_uro_development_area xml_real64, uro_building_details{}.uro_building_details_uro_development_area_units xml_buffer, uro_building_details{}.uro_building_details_uro_total_floor_area xml_real64, uro_building_details{}.uro_building_details_uro_total_floor_area_units xml_buffer, uro_building_details{}.uro_building_details_uro_building_structure_type xml_buffer, uro_building_details{}.uro_building_details_uro_building_structure_type_codeSpace xml_buffer, uro_building_details{}.uro_building_details_uro_fireproof_structure_type xml_buffer, uro_building_details{}.uro_building_details_uro_fireproof_structure_type_codeSpace xml_buffer, uro_building_details{}.uro_building_details_uro_implementing_body xml_buffer, uro_building_details{}.uro_building_details_uro_urban_plan_type xml_buffer, uro_building_details{}.uro_building_details_uro_urban_plan_type_codeSpace xml_buffer, uro_building_details{}.uro_building_details_uro_districts_and_zones_type xml_buffer, uro_building_details{}.uro_building_details_uro_districts_and_zones_type_codeSpace xml_buffer,
      uro_building_details{}.uro_building_details_uro_land_use_plan_type xml_buffer, uro_building_details{}.uro_building_details_uro_land_use_plan_type_codeSpace xml_buffer, uro_building_details{}.uro_building_details_uro_area_classification_type xml_buffer, uro_building_details{}.uro_building_details_uro_area_classification_type_codeSpace xml_buffer, uro_building_details{}.uro_building_details_uro_prefecture xml_buffer, uro_building_details{}.uro_building_details_uro_prefecture_codeSpace xml_buffer, uro_building_details{}.uro_building_details_uro_city xml_buffer, uro_building_details{}.uro_building_details_uro_city_codeSpace xml_buffer, uro_building_details{}.uro_building_details_uro_reference xml_buffer, uro_building_details{}.uro_building_details_uro_note xml_buffer, uro_building_details{}.uro_building_details_uro_survey_year xml_buffer, uro_extended_attribute{}.uro_key_value_pair_uro_key xml_buffer, uro_extended_attribute{}.uro_key_value_pair_uro_key_codeSpace xml_buffer, uro_extended_attribute{}.uro_key_value_pair_uro_string_value xml_buffer, uro_extended_attribute{}.uro_key_value_pair_uro_int_value xml_int64, uro_extended_attribute{}.uro_key_value_pair_uro_double_value xml_real64, uro_extended_attribute{}.uro_key_value_pair_uro_code_value xml_buffer, uro_extended_attribute{}.uro_key_value_pair_uro_code_value_codeSpace xml_buffer, uro_extended_attribute{}.uro_key_value_pair_uro_measured_value xml_real64, uro_extended_attribute{}.uro_key_value_pair_uro_measured_value_units xml_buffer, uro_extended_attribute{}.uro_key_value_pair_uro_date_value xml_date, uro_extended_attribute{}.uro_key_value_pair_uro_uri_value xml_buffer, uro_large_customer_facilities{}.uro_large_customer_facilities_uro_class xml_buffer, uro_large_customer_facilities{}.uro_large_customer_facilities_uro_class_codeSpace xml_buffer, uro_large_customer_facilities{}.uro_large_customer_facilities_uro_name xml_buffer, uro_large_customer_facilities{}.uro_large_customer_facilities_uro_capacity xml_int64, uro_large_customer_facilities{}.uro_large_customer_facilities_uro_owner xml_buffer, uro_large_customer_facilities{}.uro_large_customer_facilities_uro_total_floor_area xml_real64, uro_large_customer_facilities{}.uro_large_customer_facilities_uro_total_floor_area_units xml_buffer, uro_large_customer_facilities{}.uro_large_customer_facilities_uro_total_store_floor_area xml_real64,
      uro_large_customer_facilities{}.uro_large_customer_facilities_uro_total_store_floor_area_units xml_buffer, uro_large_customer_facilities{}.uro_large_customer_facilities_uro_inaugural_date xml_date, uro_large_customer_facilities{}.uro_large_customer_facilities_uro_key_tenants xml_buffer, uro_large_customer_facilities{}.uro_large_customer_facilities_uro_availability xml_boolean, uro_large_customer_facilities{}.uro_large_customer_facilities_uro_urban_plan_type xml_buffer, uro_large_customer_facilities{}.uro_large_customer_facilities_uro_urban_plan_type_codeSpace xml_buffer, uro_large_customer_facilities{}.uro_large_customer_facilities_uro_districts_and_zones_type xml_buffer, uro_large_customer_facilities{}.uro_large_customer_facilities_uro_districts_and_zones_type_codeSpace xml_buffer, uro_large_customer_facilities{}.uro_large_customer_facilities_uro_land_use_plan_type xml_buffer, uro_large_customer_facilities{}.uro_large_customer_facilities_uro_land_use_plan_type_codeSpace xml_buffer, uro_large_customer_facilities{}.uro_large_customer_facilities_uro_area_classification_type xml_buffer, uro_large_customer_facilities{}.uro_large_customer_facilities_uro_area_classification_type_codeSpace xml_buffer, uro_large_customer_facilities{}.uro_large_customer_facilities_uro_prefecture xml_buffer, uro_large_customer_facilities{}.uro_large_customer_facilities_uro_prefecture_codeSpace xml_buffer, uro_large_customer_facilities{}.uro_large_customer_facilities_uro_city xml_buffer, uro_large_customer_facilities{}.uro_large_customer_facilities_uro_city_codeSpace xml_buffer, uro_large_customer_facilities{}.uro_large_customer_facilities_uro_reference xml_buffer, uro_large_customer_facilities{}.uro_large_customer_facilities_uro_note xml_buffer, uro_large_customer_facilities{}.uro_large_customer_facilities_uro_survey_year xml_buffer
    -> Deaggregator
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> XMLFlattener
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer

Bookmark: GDBに書込み(XMLスキーマを指定)
lod2_BuildingInstallation (writer GEODATABASE_FILE_1)
    attributes: bldg_BuildingInstallation_gml_id char(50), gml_name char(50), bldg_class char(50), bldg_function char(10), bldg_Building_gml_id char(50)
lod2_OuterFloorSurface (writer GEODATABASE_FILE_1)
    attributes: bldg_OuterFloorSurface_gml_id char(50), bldg_Building_gml_id char(50)
lod2_ClosureSurface (writer GEODATABASE_FILE_1)
    attributes: bldg_ClosureSurface_gml_id char(50), bldg_Building_gml_id char(50)
lod2_RoofSurface (writer GEODATABASE_FILE_1)
    attributes: bldg_RoofSurface_gml_id char(50), bldg_Building_gml_id char(50)
lod2_WallSurface (writer GEODATABASE_FILE_1)
    attributes: bldg_WallSurface_gml_id char(50), bldg_Building_gml_id char(50)
lod2_GroundSurface (writer GEODATABASE_FILE_1)
    attributes: bldg_GroundSurface_gml_id char(50), bldg_Building_gml_id char(50)
lod2_OuterCeilingSurface (writer GEODATABASE_FILE_1)
    attributes: bldg_OuterCeilingSurface_gml_id char(50), bldg_Building_gml_id char(50)
lod1_BuildingPart (writer GEODATABASE_FILE_1)
    attributes: bldg_BuildingPart_gml_id char(50), gml_name char(50), bldg_class char(10), bldg_usage char(10), bldg_yearOfConstruction char(50), bldg_yearOfDemolition char(50), bldg_roofType char(10), bldg_measuredHeight double, bldg_storeysAboveGround integer, bldg_storeysBelowGround integer, bldg_address char(50), uro_buildingDetails_serialNumberOfBuildingCertification char(50), uro_buildingDetails_siteArea double, uro_buildingDetails_totalFloorArea double, uro_buildingDetails_buildingFootprintArea double, uro_buildingDetails_buildingRoofEdgeArea double, uro_buildingDetails_developmentArea double, uro_buildingDetails_buildingStructureType char(10), uro_buildingDetails_fireproofStructureType char(10), uro_buildingDetails_implementingBody char(50), uro_buildingDetails_urbanPlanType char(10), uro_buildingDetails_districtsAndZonesType char(10), uro_buildingDetails_landUsePlanType char(10), uro_buildingDetails_areaClassificationType char(10), uro_buildingDetails_prefecture char(2), uro_buildingDetails_city char(5), uro_buildingDetails_reference char(50), uro_buildingDetails_note char(50), uro_buildingDetails_surveyYear char(50), uro_largeCustomerFacilities_class char(10),
      uro_largeCustomerFacilities_name char(50), uro_largeCustomerFacilities_capacity integer, uro_largeCustomerFacilities_owner char(50), uro_largeCustomerFacilities_totalFloorArea double, uro_largeCustomerFacilities_totalStoreFloorArea double, uro_largeCustomerFacilities_inauguralDate char(50), uro_largeCustomerFacilities_keyTenants char(50), uro_largeCustomerFacilities_availability char(50), uro_largeCustomerFacilities_urbanPlanType char(10), uro_largeCustomerFacilities_districtsAndZonesType char(10), uro_largeCustomerFacilities_landUsePlanType char(10), uro_largeCustomerFacilities_areaClassificationType char(10), uro_largeCustomerFacilities_prefecture char(2), uro_largeCustomerFacilities_city char(5), uro_largeCustomerFacilities_reference char(50), uro_largeCustomerFacilities_note char(50), uro_largeCustomerFacilities_surveyYear char(50), uro_extendedAttribute_key2 char(10), uro_extendedAttribute_key3 char(10), uro_extendedAttribute_key4 char(10), uro_extendedAttribute_key5 char(10), uro_extendedAttribute_key6 char(10), uro_extendedAttribute_key7 char(10), uro_extendedAttribute_key8 char(10), uro_extendedAttribute_key9 char(10), uro_extendedAttribute_key10 char(10), uro_extendedAttribute_key100 char(10), uro_extendedAttribute_key101 char(10), uro_extendedAttribute_key102 char(10), uro_extendedAttribute_key103 char(10),
      uro_extendedAttribute_key104 char(10), uro_extendedAttribute_key105 char(10), uro_extendedAttribute_key106 char(10), uro_extendedAttribute_key107 char(10), uro_extendedAttribute_key108 char(10), uro_extendedAttribute_key109 char(10), uro_extendedAttribute_key110 char(10), uro_extendedAttribute_key111 char(10), uro_extendedAttribute_key112 char(10), uro_extendedAttribute_key113 char(10), uro_extendedAttribute_key114 char(10), uro_extendedAttribute_key115 char(10), uro_extendedAttribute_key116 char(10), uro_extendedAttribute_key117 char(10), uro_extendedAttribute_key118 char(10), uro_extendedAttribute_key119 char(10), uro_extendedAttribute_key120 char(10), bldg_Building_gml_id char(50)
lod2_BuildingPart (writer GEODATABASE_FILE_1)
    attributes: bldg_BuildingPart_gml_id char(50), gml_name char(50), bldg_class char(10), bldg_usage char(10), bldg_yearOfConstruction char(50), bldg_yearOfDemolition char(50), bldg_roofType char(10), bldg_measuredHeight double, bldg_storeysAboveGround integer, bldg_storeysBelowGround integer, bldg_address char(50), uro_buildingDetails_serialNumberOfBuildingCertification char(50), uro_buildingDetails_siteArea double, uro_buildingDetails_totalFloorArea double, uro_buildingDetails_buildingFootprintArea double, uro_buildingDetails_buildingRoofEdgeArea double, uro_buildingDetails_developmentArea double, uro_buildingDetails_buildingStructureType char(10), uro_buildingDetails_fireproofStructureType char(10), uro_buildingDetails_implementingBody char(50), uro_buildingDetails_urbanPlanType char(10), uro_buildingDetails_districtsAndZonesType char(10), uro_buildingDetails_landUsePlanType char(10), uro_buildingDetails_areaClassificationType char(10), uro_buildingDetails_prefecture char(2), uro_buildingDetails_city char(5), uro_buildingDetails_reference char(50), uro_buildingDetails_note char(50), uro_buildingDetails_surveyYear char(50), uro_largeCustomerFacilities_class char(10),
      uro_largeCustomerFacilities_name char(50), uro_largeCustomerFacilities_capacity integer, uro_largeCustomerFacilities_owner char(50), uro_largeCustomerFacilities_totalFloorArea double, uro_largeCustomerFacilities_totalStoreFloorArea double, uro_largeCustomerFacilities_inauguralDate char(50), uro_largeCustomerFacilities_keyTenants char(50), uro_largeCustomerFacilities_availability char(50), uro_largeCustomerFacilities_urbanPlanType char(10), uro_largeCustomerFacilities_districtsAndZonesType char(10), uro_largeCustomerFacilities_landUsePlanType char(10), uro_largeCustomerFacilities_areaClassificationType char(10), uro_largeCustomerFacilities_prefecture char(2), uro_largeCustomerFacilities_city char(5), uro_largeCustomerFacilities_reference char(50), uro_largeCustomerFacilities_note char(50), uro_largeCustomerFacilities_surveyYear char(50), uro_extendedAttribute_key2 char(10), uro_extendedAttribute_key3 char(10), uro_extendedAttribute_key4 char(10), uro_extendedAttribute_key5 char(10), uro_extendedAttribute_key6 char(10), uro_extendedAttribute_key7 char(10), uro_extendedAttribute_key8 char(10), uro_extendedAttribute_key9 char(10), uro_extendedAttribute_key10 char(10), uro_extendedAttribute_key100 char(10), uro_extendedAttribute_key101 char(10), uro_extendedAttribute_key102 char(10), uro_extendedAttribute_key103 char(10),
      uro_extendedAttribute_key104 char(10), uro_extendedAttribute_key105 char(10), uro_extendedAttribute_key106 char(10), uro_extendedAttribute_key107 char(10), uro_extendedAttribute_key108 char(10), uro_extendedAttribute_key109 char(10), uro_extendedAttribute_key110 char(10), uro_extendedAttribute_key111 char(10), uro_extendedAttribute_key112 char(10), uro_extendedAttribute_key113 char(10), uro_extendedAttribute_key114 char(10), uro_extendedAttribute_key115 char(10), uro_extendedAttribute_key116 char(10), uro_extendedAttribute_key117 char(10), uro_extendedAttribute_key118 char(10), uro_extendedAttribute_key119 char(10), uro_extendedAttribute_key120 char(10), bldg_Building_gml_id char(50)
lod0_Building (writer GEODATABASE_FILE_1)
    attributes: bldg_Building_gml_id char(50), gml_name char(50), bldg_class char(10), bldg_usage char(10), bldg_yearOfConstruction char(50), bldg_yearOfDemolition char(50), bldg_roofType char(10), bldg_measuredHeight double, bldg_storeysAboveGround integer, bldg_storeysBelowGround integer, bldg_address char(50), uro_buildingDetails_serialNumberOfBuildingCertification char(50), uro_buildingDetails_siteArea double, uro_buildingDetails_totalFloorArea double, uro_buildingDetails_buildingFootprintArea double, uro_buildingDetails_buildingRoofEdgeArea double, uro_buildingDetails_developmentArea double, uro_buildingDetails_buildingStructureType char(10), uro_buildingDetails_fireproofStructureType char(10), uro_buildingDetails_implementingBody char(50), uro_buildingDetails_urbanPlanType char(10), uro_buildingDetails_districtsAndZonesType char(10), uro_buildingDetails_landUsePlanType char(10), uro_buildingDetails_areaClassificationType char(10), uro_buildingDetails_prefecture char(2), uro_buildingDetails_city char(5), uro_buildingDetails_reference char(50), uro_buildingDetails_note char(50), uro_buildingDetails_surveyYear char(50), uro_largeCustomerFacilities_class char(10),
      uro_largeCustomerFacilities_name char(50), uro_largeCustomerFacilities_capacity integer, uro_largeCustomerFacilities_owner char(50), uro_largeCustomerFacilities_totalFloorArea double, uro_largeCustomerFacilities_totalStoreFloorArea double, uro_largeCustomerFacilities_inauguralDate char(50), uro_largeCustomerFacilities_keyTenants char(50), uro_largeCustomerFacilities_availability char(50), uro_largeCustomerFacilities_urbanPlanType char(10), uro_largeCustomerFacilities_districtsAndZonesType char(10), uro_largeCustomerFacilities_landUsePlanType char(10), uro_largeCustomerFacilities_areaClassificationType char(10), uro_largeCustomerFacilities_prefecture char(2), uro_largeCustomerFacilities_city char(5), uro_largeCustomerFacilities_reference char(50), uro_largeCustomerFacilities_note char(50), uro_largeCustomerFacilities_surveyYear char(50), xml_genericAttributeSet char(10000), uro_extendedAttribute_key2 char(10), uro_extendedAttribute_key3 char(10), uro_extendedAttribute_key4 char(10), uro_extendedAttribute_key5 char(10), uro_extendedAttribute_key6 char(10), uro_extendedAttribute_key7 char(10), uro_extendedAttribute_key8 char(10), uro_extendedAttribute_key9 char(10), uro_extendedAttribute_key10 char(10), uro_extendedAttribute_key100 char(10), uro_extendedAttribute_key101 char(10), uro_extendedAttribute_key102 char(10),
      uro_extendedAttribute_key103 char(10), uro_extendedAttribute_key104 char(10), uro_extendedAttribute_key105 char(10), uro_extendedAttribute_key106 char(10), uro_extendedAttribute_key107 char(10), uro_extendedAttribute_key108 char(10), uro_extendedAttribute_key109 char(10), uro_extendedAttribute_key110 char(10), uro_extendedAttribute_key111 char(10), uro_extendedAttribute_key112 char(10), uro_extendedAttribute_key113 char(10), uro_extendedAttribute_key114 char(10), uro_extendedAttribute_key115 char(10), uro_extendedAttribute_key116 char(10), uro_extendedAttribute_key117 char(10), uro_extendedAttribute_key118 char(10), uro_extendedAttribute_key119 char(10), uro_extendedAttribute_key120 char(10)
lod1_Building (writer GEODATABASE_FILE_1)
    attributes: bldg_Building_gml_id char(50), gml_name char(50), bldg_class char(10), bldg_usage char(10), bldg_yearOfConstruction char(50), bldg_yearOfDemolition char(50), bldg_roofType char(10), bldg_measuredHeight double, bldg_storeysAboveGround integer, bldg_storeysBelowGround integer, bldg_address char(50), uro_buildingDetails_serialNumberOfBuildingCertification char(50), uro_buildingDetails_siteArea double, uro_buildingDetails_totalFloorArea double, uro_buildingDetails_buildingFootprintArea double, uro_buildingDetails_buildingRoofEdgeArea double, uro_buildingDetails_developmentArea double, uro_buildingDetails_buildingStructureType char(10), uro_buildingDetails_fireproofStructureType char(10), uro_buildingDetails_implementingBody char(50), uro_buildingDetails_urbanPlanType char(10), uro_buildingDetails_districtsAndZonesType char(10), uro_buildingDetails_landUsePlanType char(10), uro_buildingDetails_areaClassificationType char(10), uro_buildingDetails_prefecture char(2), uro_buildingDetails_city char(5), uro_buildingDetails_reference char(50), uro_buildingDetails_note char(50), uro_buildingDetails_surveyYear char(50), uro_largeCustomerFacilities_class char(10),
      uro_largeCustomerFacilities_name char(50), uro_largeCustomerFacilities_capacity integer, uro_largeCustomerFacilities_owner char(50), uro_largeCustomerFacilities_totalFloorArea double, uro_largeCustomerFacilities_totalStoreFloorArea double, uro_largeCustomerFacilities_inauguralDate char(50), uro_largeCustomerFacilities_keyTenants char(50), uro_largeCustomerFacilities_availability char(50), uro_largeCustomerFacilities_urbanPlanType char(10), uro_largeCustomerFacilities_districtsAndZonesType char(10), uro_largeCustomerFacilities_landUsePlanType char(10), uro_largeCustomerFacilities_areaClassificationType char(10), uro_largeCustomerFacilities_prefecture char(2), uro_largeCustomerFacilities_city char(5), uro_largeCustomerFacilities_reference char(50), uro_largeCustomerFacilities_note char(50), uro_largeCustomerFacilities_surveyYear char(50), xml_genericAttributeSet char(10000), uro_extendedAttribute_key2 char(10), uro_extendedAttribute_key3 char(10), uro_extendedAttribute_key4 char(10), uro_extendedAttribute_key5 char(10), uro_extendedAttribute_key6 char(10), uro_extendedAttribute_key7 char(10), uro_extendedAttribute_key8 char(10), uro_extendedAttribute_key9 char(10), uro_extendedAttribute_key10 char(10), uro_extendedAttribute_key100 char(10), uro_extendedAttribute_key101 char(10), uro_extendedAttribute_key102 char(10),
      uro_extendedAttribute_key103 char(10), uro_extendedAttribute_key104 char(10), uro_extendedAttribute_key105 char(10), uro_extendedAttribute_key106 char(10), uro_extendedAttribute_key107 char(10), uro_extendedAttribute_key108 char(10), uro_extendedAttribute_key109 char(10), uro_extendedAttribute_key110 char(10), uro_extendedAttribute_key111 char(10), uro_extendedAttribute_key112 char(10), uro_extendedAttribute_key113 char(10), uro_extendedAttribute_key114 char(10), uro_extendedAttribute_key115 char(10), uro_extendedAttribute_key116 char(10), uro_extendedAttribute_key117 char(10), uro_extendedAttribute_key118 char(10), uro_extendedAttribute_key119 char(10), uro_extendedAttribute_key120 char(10)
lod2_Building (writer GEODATABASE_FILE_1)
    attributes: bldg_Building_gml_id char(50), gml_name char(50), bldg_class char(10), bldg_usage char(10), bldg_yearOfConstruction char(50), bldg_yearOfDemolition char(50), bldg_roofType char(10), bldg_measuredHeight double, bldg_storeysAboveGround integer, bldg_storeysBelowGround integer, bldg_address char(50), uro_buildingDetails_serialNumberOfBuildingCertification char(50), uro_buildingDetails_siteArea double, uro_buildingDetails_totalFloorArea double, uro_buildingDetails_buildingFootprintArea double, uro_buildingDetails_buildingRoofEdgeArea double, uro_buildingDetails_developmentArea double, uro_buildingDetails_buildingStructureType char(10), uro_buildingDetails_fireproofStructureType char(10), uro_buildingDetails_implementingBody char(50), uro_buildingDetails_urbanPlanType char(10), uro_buildingDetails_districtsAndZonesType char(10), uro_buildingDetails_landUsePlanType char(10), uro_buildingDetails_areaClassificationType char(10), uro_buildingDetails_prefecture char(2), uro_buildingDetails_city char(5), uro_buildingDetails_reference char(50), uro_buildingDetails_note char(50), uro_buildingDetails_surveyYear char(50), uro_largeCustomerFacilities_class char(10),
      uro_largeCustomerFacilities_name char(50), uro_largeCustomerFacilities_capacity integer, uro_largeCustomerFacilities_owner char(50), uro_largeCustomerFacilities_totalFloorArea double, uro_largeCustomerFacilities_totalStoreFloorArea double, uro_largeCustomerFacilities_inauguralDate char(50), uro_largeCustomerFacilities_keyTenants char(50), uro_largeCustomerFacilities_availability char(50), uro_largeCustomerFacilities_urbanPlanType char(10), uro_largeCustomerFacilities_districtsAndZonesType char(10), uro_largeCustomerFacilities_landUsePlanType char(10), uro_largeCustomerFacilities_areaClassificationType char(10), uro_largeCustomerFacilities_prefecture char(2), uro_largeCustomerFacilities_city char(5), uro_largeCustomerFacilities_reference char(50), uro_largeCustomerFacilities_note char(50), uro_largeCustomerFacilities_surveyYear char(50), xml_genericAttributeSet char(10000), uro_extendedAttribute_key2 char(10), uro_extendedAttribute_key3 char(10), uro_extendedAttribute_key4 char(10), uro_extendedAttribute_key5 char(10), uro_extendedAttribute_key6 char(10), uro_extendedAttribute_key7 char(10), uro_extendedAttribute_key8 char(10), uro_extendedAttribute_key9 char(10), uro_extendedAttribute_key10 char(10), uro_extendedAttribute_key100 char(10), uro_extendedAttribute_key101 char(10), uro_extendedAttribute_key102 char(10),
      uro_extendedAttribute_key103 char(10), uro_extendedAttribute_key104 char(10), uro_extendedAttribute_key105 char(10), uro_extendedAttribute_key106 char(10), uro_extendedAttribute_key107 char(10), uro_extendedAttribute_key108 char(10), uro_extendedAttribute_key109 char(10), uro_extendedAttribute_key110 char(10), uro_extendedAttribute_key111 char(10), uro_extendedAttribute_key112 char(10), uro_extendedAttribute_key113 char(10), uro_extendedAttribute_key114 char(10), uro_extendedAttribute_key115 char(10), uro_extendedAttribute_key116 char(10), uro_extendedAttribute_key117 char(10), uro_extendedAttribute_key118 char(10), uro_extendedAttribute_key119 char(10), uro_extendedAttribute_key120 char(10)

Bookmark: 標準製品仕様に合わせて属性を抽出（拡張属性および汎用属性は含まない）
Note: ・リスト属性はインデックス「0」を指定して抽出
AttributeCreator_3
    ATTR_TABLE:
      SET_TO citygml_fnction_0 = @Value(citygml_function{0})
      SET_TO citygml_usage_0 = @Value(citygml_usage{0})
      SET_TO uro_building_details_uro_serial_number_of_building_certification_0 = @Value(uro_building_details{0}.uro_building_details_uro_serial_number_of_building_certification)
      SET_TO uro_building_details_uro_site_area_0 = @Value(uro_building_details{0}.uro_building_details_uro_site_area)
      SET_TO uro_building_details_uro_total_floor_area_0 = @Value(uro_building_details{0}.uro_building_details_uro_total_floor_area)
      SET_TO uro_building_details_uro_building_footprint_area_0 = @Value(uro_building_details{0}.uro_building_details_uro_building_footprint_area)
      SET_TO uro_building_details_uro_building_roof_edge_area_0 = @Value(uro_building_details{0}.uro_building_details_uro_building_roof_edge_area)
      SET_TO uro_building_details_uro_development_area_0 = @Value(uro_building_details{0}.uro_building_details_uro_development_area)
      SET_TO uro_building_details_uro_building_structure_type_0 = @Value(uro_building_details{0}.uro_building_details_uro_building_structure_type)
      SET_TO uro_building_details_uro_fireproof_structure_type_0 = @Value(uro_building_details{0}.uro_building_details_uro_fireproof_structure_type)
      SET_TO uro_building_details_uro_implementing_body_0 = @Value(uro_building_details{0}.uro_building_details_uro_implementing_body)
      SET_TO uro_building_details_uro_urban_plan_type_0 = @Value(uro_building_details{0}.uro_building_details_uro_urban_plan_type)
      SET_TO uro_building_details_uro_districts_and_zones_type_0 = @Value(uro_building_details{0}.uro_building_details_uro_districts_and_zones_type)
      SET_TO uro_building_details_uro_land_use_plan_type_0 = @Value(uro_building_details{0}.uro_building_details_uro_land_use_plan_type)
      SET_TO uro_building_details_uro_area_classification_type_0 = @Value(uro_building_details{0}.uro_building_details_uro_area_classification_type)
      SET_TO uro_building_details_uro_prefecture_0 = @Value(uro_building_details{0}.uro_building_details_uro_prefecture)
      SET_TO uro_building_details_uro_city_0 = @Value(uro_building_details{0}.uro_building_details_uro_city)
      SET_TO uro_building_details_uro_reference_0 = @Value(uro_building_details{0}.uro_building_details_uro_reference)
      SET_TO uro_building_details_uro_note_0 = @Value(uro_building_details{0}.uro_building_details_uro_note)
      SET_TO uro_building_details_uro_survey_year_0 = @Value(uro_building_details{0}.uro_building_details_uro_survey_year)
      SET_TO uro_large_customer_facilities_uro_class_0 = @Value(uro_large_customer_facilities{0}.uro_large_customer_facilities_uro_class)
      SET_TO uro_large_customer_facilities_uro_name_0 = @Value(uro_large_customer_facilities{0}.uro_large_customer_facilities_uro_name)
      SET_TO uro_large_customer_facilities_uro_capacity_0 = @Value(uro_large_customer_facilities{0}.uro_large_customer_facilities_uro_capacity)
      SET_TO uro_large_customer_facilities_uro_owner_0 = @Value(uro_large_customer_facilities{0}.uro_large_customer_facilities_uro_owner)
      SET_TO uro_large_customer_facilities_uro_total_floor_area_0 = @Value(uro_large_customer_facilities{0}.uro_large_customer_facilities_uro_total_floor_area)
      SET_TO uro_large_customer_facilities_uro_total_store_floor_area_0 = @Value(uro_large_customer_facilities{0}.uro_large_customer_facilities_uro_total_store_floor_area)
      SET_TO uro_large_customer_facilities_uro_inaugural_date_0 = @Value(uro_large_customer_facilities{0}.uro_large_customer_facilities_uro_inaugural_date)
      SET_TO uro_large_customer_facilities_uro_key_tenants_0 = @Value(uro_large_customer_facilities{0}.uro_large_customer_facilities_uro_key_tenants)
      SET_TO uro_large_customer_facilities_uro_availability_0 = @Value(uro_large_customer_facilities{0}.uro_large_customer_facilities_uro_availability)
      SET_TO uro_large_customer_facilities_uro_urban_plan_type_0 = @Value(uro_large_customer_facilities{0}.uro_large_customer_facilities_uro_urban_plan_type)
      SET_TO uro_large_customer_facilities_uro_districts_and_zones_type_0 = @Value(uro_large_customer_facilities{0}.uro_large_customer_facilities_uro_districts_and_zones_type)
      SET_TO uro_large_customer_facilities_uro_land_use_plan_type_0 = @Value(uro_large_customer_facilities{0}.uro_large_customer_facilities_uro_land_use_plan_type)
      SET_TO uro_large_customer_facilities_uro_area_classification_type_0 = @Value(uro_large_customer_facilities{0}.uro_large_customer_facilities_uro_area_classification_type)
      SET_TO uro_large_customer_facilities_uro_prefecture_0 = @Value(uro_large_customer_facilities{0}.uro_large_customer_facilities_uro_prefecture)
      SET_TO uro_large_customer_facilities_uro_city_0 = @Value(uro_large_customer_facilities{0}.uro_large_customer_facilities_uro_city)
      SET_TO uro_large_customer_facilities_uro_reference_0 = @Value(uro_large_customer_facilities{0}.uro_large_customer_facilities_uro_reference)
      SET_TO uro_large_customer_facilities_uro_note_0 = @Value(uro_large_customer_facilities{0}.uro_large_customer_facilities_uro_note)
      SET_TO uro_large_customer_facilities_uro_survey_year_0 = @Value(uro_large_customer_facilities{0}.uro_large_customer_facilities_uro_survey_year)
    -> AttributeManager_11
AttributeManager_11
    ATTR_TABLE:
      RENAME_SET_VALUE gml_id > bldg_BuildingPart_gml_id
      RENAME_SET_VALUE gml_parent_id > bldg_Building_gml_id
      REMOVE citygml_target_uri
      REMOVE citygml_feature_role
      REMOVE citygml_feature_role_attr_name
      REMOVE citygml_feature_role_attr_val
      REMOVE gml_description
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      RENAME_SET_VALUE citygml_class > bldg_class
      REMOVE citygml_class_codeSpace
      REMOVE citygml_function{}
      REMOVE citygml_function{}.codeSpace
      REMOVE citygml_usage{}
      REMOVE citygml_usage{}.codeSpace
      RENAME_SET_VALUE citygml_usage_0 > bldg_usage
      RENAME_SET_VALUE citygml_year_of_construction > bldg_yearOfConstruction
      RENAME_SET_VALUE citygml_year_of_demolition > bldg_yearOfDemolition
      RENAME_SET_VALUE citygml_roof_type > bldg_roofType
      REMOVE citygml_roof_type_codeSpace
      RENAME_SET_VALUE citygml_measured_height > bldg_measuredHeight
      REMOVE citygml_measured_height_units
      RENAME_SET_VALUE citygml_storeys_above_ground > bldg_storeysAboveGround
      RENAME_SET_VALUE citygml_storeys_below_ground > bldg_storeysBelowGround
      REMOVE citygml_storey_heights_above_ground
      REMOVE citygml_storey_heights_above_ground_units
      REMOVE citygml_storey_heights_below_ground
      REMOVE citygml_storey_heights_below_ground_units
      REMOVE citygml_outer_building_installation{}.xlink_href
      REMOVE citygml_interior_building_installation{}.xlink_href
      REMOVE citygml_bounded_by{}.xlink_href
      REMOVE citygml_level_of_detail{}
      REMOVE citygml_interior_room{}.xlink_href
      REMOVE citygml_consists_of_building_part{}.xlink_href
      REMOVE citygml_address{}.xlink_href
      RENAME_SET_VALUE Address > bldg_address
      REMOVE uro_building_details{}.uro_building_details_uro_serial_number_of_building_certification
      REMOVE uro_building_details{}.uro_building_details_uro_site_area
      REMOVE uro_building_details{}.uro_building_details_uro_site_area_units
      REMOVE uro_building_details{}.uro_building_details_uro_building_footprint_area
      REMOVE uro_building_details{}.uro_building_details_uro_building_footprint_area_units
      REMOVE uro_building_details{}.uro_building_details_uro_building_roof_edge_area
      REMOVE uro_building_details{}.uro_building_details_uro_building_roof_edge_area_units
      REMOVE uro_building_details{}.uro_building_details_uro_development_area
      REMOVE uro_building_details{}.uro_building_details_uro_development_area_units
      REMOVE uro_building_details{}.uro_building_details_uro_total_floor_area
      REMOVE uro_building_details{}.uro_building_details_uro_total_floor_area_units
      REMOVE uro_building_details{}.uro_building_details_uro_building_structure_type
      REMOVE uro_building_details{}.uro_building_details_uro_building_structure_type_codeSpace
      REMOVE uro_building_details{}.uro_building_details_uro_fireproof_structure_type
      REMOVE uro_building_details{}.uro_building_details_uro_fireproof_structure_type_codeSpace
      REMOVE uro_building_details{}.uro_building_details_uro_implementing_body
      REMOVE uro_building_details{}.uro_building_details_uro_urban_plan_type
      REMOVE uro_building_details{}.uro_building_details_uro_urban_plan_type_codeSpace
      REMOVE uro_building_details{}.uro_building_details_uro_districts_and_zones_type
      REMOVE uro_building_details{}.uro_building_details_uro_districts_and_zones_type_codeSpace
      REMOVE uro_building_details{}.uro_building_details_uro_land_use_plan_type
      REMOVE uro_building_details{}.uro_building_details_uro_area_classification_type
      REMOVE uro_building_details{}.uro_building_details_uro_area_classification_type_codeSpace
      REMOVE uro_building_details{}.uro_building_details_uro_land_use_plan_type_codeSpace
      REMOVE uro_building_details{}.uro_building_details_uro_prefecture
      REMOVE uro_building_details{}.uro_building_details_uro_prefecture_codeSpace
      REMOVE uro_building_details{}.uro_building_details_uro_city
      REMOVE uro_building_details{}.uro_building_details_uro_city_codeSpace
      REMOVE uro_building_details{}.uro_building_details_uro_reference
      REMOVE uro_building_details{}.uro_building_details_uro_note
      REMOVE uro_building_details{}.uro_building_details_uro_survey_year
      REMOVE uro_extended_attribute{}.uro_key_value_pair_uro_key
      REMOVE uro_extended_attribute{}.uro_key_value_pair_uro_key_codeSpace
      REMOVE uro_extended_attribute{}.uro_key_value_pair_uro_string_value
      REMOVE uro_extended_attribute{}.uro_key_value_pair_uro_int_value
      REMOVE uro_extended_attribute{}.uro_key_value_pair_uro_double_value
      REMOVE uro_extended_attribute{}.uro_key_value_pair_uro_code_value
      REMOVE uro_extended_attribute{}.uro_key_value_pair_uro_code_value_codeSpace
      REMOVE uro_extended_attribute{}.uro_key_value_pair_uro_measured_value
      REMOVE uro_extended_attribute{}.uro_key_value_pair_uro_measured_value_units
      REMOVE uro_extended_attribute{}.uro_key_value_pair_uro_date_value
      REMOVE uro_extended_attribute{}.uro_key_value_pair_uro_uri_value
      REMOVE uro_large_customer_facilities{}.uro_large_customer_facilities_uro_class
      REMOVE uro_large_customer_facilities{}.uro_large_customer_facilities_uro_class_codeSpace
      REMOVE uro_large_customer_facilities{}.uro_large_customer_facilities_uro_name
      REMOVE uro_large_customer_facilities{}.uro_large_customer_facilities_uro_capacity
      REMOVE uro_large_customer_facilities{}.uro_large_customer_facilities_uro_owner
      REMOVE uro_large_customer_facilities{}.uro_large_customer_facilities_uro_total_floor_area
      REMOVE uro_large_customer_facilities{}.uro_large_customer_facilities_uro_total_floor_area_units
      REMOVE uro_large_customer_facilities{}.uro_large_customer_facilities_uro_total_store_floor_area
      REMOVE uro_large_customer_facilities{}.uro_large_customer_facilities_uro_total_store_floor_area_units
      REMOVE uro_large_customer_facilities{}.uro_large_customer_facilities_uro_inaugural_date
      REMOVE uro_large_customer_facilities{}.uro_large_customer_facilities_uro_key_tenants
      REMOVE uro_large_customer_facilities{}.uro_large_customer_facilities_uro_availability
      REMOVE uro_large_customer_facilities{}.uro_large_customer_facilities_uro_urban_plan_type
      REMOVE uro_large_customer_facilities{}.uro_large_customer_facilities_uro_urban_plan_type_codeSpace
      REMOVE uro_large_customer_facilities{}.uro_large_customer_facilities_uro_districts_and_zones_type
      REMOVE uro_large_customer_facilities{}.uro_large_customer_facilities_uro_districts_and_zones_type_codeSpace
      REMOVE uro_large_customer_facilities{}.uro_large_customer_facilities_uro_land_use_plan_type
      REMOVE uro_large_customer_facilities{}.uro_large_customer_facilities_uro_land_use_plan_type_codeSpace
      REMOVE uro_large_customer_facilities{}.uro_large_customer_facilities_uro_area_classification_type
      REMOVE uro_large_customer_facilities{}.uro_large_customer_facilities_uro_area_classification_type_codeSpace
      REMOVE uro_large_customer_facilities{}.uro_large_customer_facilities_uro_prefecture
      REMOVE uro_large_customer_facilities{}.uro_large_customer_facilities_uro_prefecture_codeSpace
      REMOVE uro_large_customer_facilities{}.uro_large_customer_facilities_uro_city
      REMOVE uro_large_customer_facilities{}.uro_large_customer_facilities_uro_city_codeSpace
      REMOVE uro_large_customer_facilities{}.uro_large_customer_facilities_uro_reference
      REMOVE uro_large_customer_facilities{}.uro_large_customer_facilities_uro_note
      REMOVE uro_large_customer_facilities{}.uro_large_customer_facilities_uro_survey_year
      REMOVE citygml_fnction_0
      RENAME_SET_VALUE uro_building_details_uro_serial_number_of_building_certification_0 > uro_buildingDetails_serialNumberOfBuildingCertification
      RENAME_SET_VALUE uro_building_details_uro_site_area_0 > uro_buildingDetails_siteArea
      RENAME_SET_VALUE uro_building_details_uro_total_floor_area_0 > uro_buildingDetails_totalFloorArea
      RENAME_SET_VALUE uro_building_details_uro_building_footprint_area_0 > uro_buildingDetails_buildingFootprintArea
      RENAME_SET_VALUE uro_building_details_uro_building_roof_edge_area_0 > uro_buildingDetails_buildingRoofEdgeArea
      RENAME_SET_VALUE uro_building_details_uro_development_area_0 > uro_buildingDetails_developmentArea
      RENAME_SET_VALUE uro_building_details_uro_building_structure_type_0 > uro_buildingDetails_buildingStructureType
      RENAME_SET_VALUE uro_building_details_uro_fireproof_structure_type_0 > uro_buildingDetails_fireproofStructureType
      RENAME_SET_VALUE uro_building_details_uro_implementing_body_0 > uro_buildingDetails_implementingBody
      RENAME_SET_VALUE uro_building_details_uro_urban_plan_type_0 > uro_buildingDetails_urbanPlanType
      RENAME_SET_VALUE uro_building_details_uro_districts_and_zones_type_0 > uro_buildingDetails_districtsAndZonesType
      RENAME_SET_VALUE uro_building_details_uro_land_use_plan_type_0 > uro_buildingDetails_landUsePlanType
      RENAME_SET_VALUE uro_building_details_uro_area_classification_type_0 > uro_buildingDetails_areaClassificationType
      RENAME_SET_VALUE uro_building_details_uro_prefecture_0 > uro_buildingDetails_prefecture
      RENAME_SET_VALUE uro_building_details_uro_city_0 > uro_buildingDetails_city
      RENAME_SET_VALUE uro_building_details_uro_reference_0 > uro_buildingDetails_reference
      RENAME_SET_VALUE uro_building_details_uro_note_0 > uro_buildingDetails_note
      RENAME_SET_VALUE uro_building_details_uro_survey_year_0 > uro_buildingDetails_surveyYear
      RENAME_SET_VALUE uro_large_customer_facilities_uro_class_0 > uro_largeCustomerFacilities_class
      RENAME_SET_VALUE uro_large_customer_facilities_uro_name_0 > uro_largeCustomerFacilities_name
      RENAME_SET_VALUE uro_large_customer_facilities_uro_capacity_0 > uro_largeCustomerFacilities_capacity
      RENAME_SET_VALUE uro_large_customer_facilities_uro_owner_0 > uro_largeCustomerFacilities_owner
      RENAME_SET_VALUE uro_large_customer_facilities_uro_total_floor_area_0 > uro_largeCustomerFacilities_totalFloorArea
      RENAME_SET_VALUE uro_large_customer_facilities_uro_total_store_floor_area_0 > uro_largeCustomerFacilities_totalStoreFloorArea
      RENAME_SET_VALUE uro_large_customer_facilities_uro_inaugural_date_0 > uro_largeCustomerFacilities_inauguralDate
      RENAME_SET_VALUE uro_large_customer_facilities_uro_key_tenants_0 > uro_largeCustomerFacilities_keyTenants
      RENAME_SET_VALUE uro_large_customer_facilities_uro_availability_0 > uro_largeCustomerFacilities_availability
      RENAME_SET_VALUE uro_large_customer_facilities_uro_urban_plan_type_0 > uro_largeCustomerFacilities_urbanPlanType
      RENAME_SET_VALUE uro_large_customer_facilities_uro_districts_and_zones_type_0 > uro_largeCustomerFacilities_districtsAndZonesType
      RENAME_SET_VALUE uro_large_customer_facilities_uro_land_use_plan_type_0 > uro_largeCustomerFacilities_landUsePlanType
      RENAME_SET_VALUE uro_large_customer_facilities_uro_area_classification_type_0 > uro_largeCustomerFacilities_areaClassificationType
      RENAME_SET_VALUE uro_large_customer_facilities_uro_prefecture_0 > uro_largeCustomerFacilities_prefecture
      RENAME_SET_VALUE uro_large_customer_facilities_uro_city_0 > uro_largeCustomerFacilities_city
      RENAME_SET_VALUE uro_large_customer_facilities_uro_reference_0 > uro_largeCustomerFacilities_reference
      RENAME_SET_VALUE uro_large_customer_facilities_uro_note_0 > uro_largeCustomerFacilities_note
      RENAME_SET_VALUE uro_large_customer_facilities_uro_survey_year_0 > uro_largeCustomerFacilities_surveyYear
      REMOVE citygml_address
    -> FeatureJoiner_5 [LEFT]
Note: ・リスト属性はインデックス「0」を指定して抽出
AttributeCreator
    ATTR_TABLE:
      SET_TO citygml_fnction_0 = @Value(citygml_function{0})
      SET_TO citygml_usage_0 = @Value(citygml_usage{0})
      SET_TO uro_building_details_uro_serial_number_of_building_certification_0 = @Value(uro_building_details{0}.uro_building_details_uro_serial_number_of_building_certification)
      SET_TO uro_building_details_uro_site_area_0 = @Value(uro_building_details{0}.uro_building_details_uro_site_area)
      SET_TO uro_building_details_uro_total_floor_area_0 = @Value(uro_building_details{0}.uro_building_details_uro_total_floor_area)
      SET_TO uro_building_details_uro_building_footprint_area_0 = @Value(uro_building_details{0}.uro_building_details_uro_building_footprint_area)
      SET_TO uro_building_details_uro_building_roof_edge_area_0 = @Value(uro_building_details{0}.uro_building_details_uro_building_roof_edge_area)
      SET_TO uro_building_details_uro_development_area_0 = @Value(uro_building_details{0}.uro_building_details_uro_development_area)
      SET_TO uro_building_details_uro_building_structure_type_0 = @Value(uro_building_details{0}.uro_building_details_uro_building_structure_type)
      SET_TO uro_building_details_uro_fireproof_structure_type_0 = @Value(uro_building_details{0}.uro_building_details_uro_fireproof_structure_type)
      SET_TO uro_building_details_uro_implementing_body_0 = @Value(uro_building_details{0}.uro_building_details_uro_implementing_body)
      SET_TO uro_building_details_uro_urban_plan_type_0 = @Value(uro_building_details{0}.uro_building_details_uro_urban_plan_type)
      SET_TO uro_building_details_uro_districts_and_zones_type_0 = @Value(uro_building_details{0}.uro_building_details_uro_districts_and_zones_type)
      SET_TO uro_building_details_uro_land_use_plan_type_0 = @Value(uro_building_details{0}.uro_building_details_uro_land_use_plan_type)
      SET_TO uro_building_details_uro_area_classification_type_0 = @Value(uro_building_details{0}.uro_building_details_uro_area_classification_type)
      SET_TO uro_building_details_uro_prefecture_0 = @Value(uro_building_details{0}.uro_building_details_uro_prefecture)
      SET_TO uro_building_details_uro_city_0 = @Value(uro_building_details{0}.uro_building_details_uro_city)
      SET_TO uro_building_details_uro_reference_0 = @Value(uro_building_details{0}.uro_building_details_uro_reference)
      SET_TO uro_building_details_uro_note_0 = @Value(uro_building_details{0}.uro_building_details_uro_note)
      SET_TO uro_building_details_uro_survey_year_0 = @Value(uro_building_details{0}.uro_building_details_uro_survey_year)
      SET_TO uro_large_customer_facilities_uro_class_0 = @Value(uro_large_customer_facilities{0}.uro_large_customer_facilities_uro_class)
      SET_TO uro_large_customer_facilities_uro_name_0 = @Value(uro_large_customer_facilities{0}.uro_large_customer_facilities_uro_name)
      SET_TO uro_large_customer_facilities_uro_capacity_0 = @Value(uro_large_customer_facilities{0}.uro_large_customer_facilities_uro_capacity)
      SET_TO uro_large_customer_facilities_uro_owner_0 = @Value(uro_large_customer_facilities{0}.uro_large_customer_facilities_uro_owner)
      SET_TO uro_large_customer_facilities_uro_total_floor_area_0 = @Value(uro_large_customer_facilities{0}.uro_large_customer_facilities_uro_total_floor_area)
      SET_TO uro_large_customer_facilities_uro_total_store_floor_area_0 = @Value(uro_large_customer_facilities{0}.uro_large_customer_facilities_uro_total_store_floor_area)
      SET_TO uro_large_customer_facilities_uro_inaugural_date_0 = @Value(uro_large_customer_facilities{0}.uro_large_customer_facilities_uro_inaugural_date)
      SET_TO uro_large_customer_facilities_uro_key_tenants_0 = @Value(uro_large_customer_facilities{0}.uro_large_customer_facilities_uro_key_tenants)
      SET_TO uro_large_customer_facilities_uro_availability_0 = @Value(uro_large_customer_facilities{0}.uro_large_customer_facilities_uro_availability)
      SET_TO uro_large_customer_facilities_uro_urban_plan_type_0 = @Value(uro_large_customer_facilities{0}.uro_large_customer_facilities_uro_urban_plan_type)
      SET_TO uro_large_customer_facilities_uro_districts_and_zones_type_0 = @Value(uro_large_customer_facilities{0}.uro_large_customer_facilities_uro_districts_and_zones_type)
      SET_TO uro_large_customer_facilities_uro_land_use_plan_type_0 = @Value(uro_large_customer_facilities{0}.uro_large_customer_facilities_uro_land_use_plan_type)
      SET_TO uro_large_customer_facilities_uro_area_classification_type_0 = @Value(uro_large_customer_facilities{0}.uro_large_customer_facilities_uro_area_classification_type)
      SET_TO uro_large_customer_facilities_uro_prefecture_0 = @Value(uro_large_customer_facilities{0}.uro_large_customer_facilities_uro_prefecture)
      SET_TO uro_large_customer_facilities_uro_city_0 = @Value(uro_large_customer_facilities{0}.uro_large_customer_facilities_uro_city)
      SET_TO uro_large_customer_facilities_uro_reference_0 = @Value(uro_large_customer_facilities{0}.uro_large_customer_facilities_uro_reference)
      SET_TO uro_large_customer_facilities_uro_note_0 = @Value(uro_large_customer_facilities{0}.uro_large_customer_facilities_uro_note)
      SET_TO uro_large_customer_facilities_uro_survey_year_0 = @Value(uro_large_customer_facilities{0}.uro_large_customer_facilities_uro_survey_year)
    -> AttributeManager
AttributeManager
    ATTR_TABLE:
      RENAME_SET_VALUE gml_id > bldg_Building_gml_id
      REMOVE gml_parent_id
      REMOVE citygml_target_uri
      REMOVE citygml_feature_role
      REMOVE citygml_feature_role_attr_name
      REMOVE citygml_feature_role_attr_val
      REMOVE gml_description
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE citygml_appearance{}.xlink_href
      RENAME_SET_VALUE citygml_class > bldg_class
      REMOVE citygml_class_codeSpace
      REMOVE citygml_function{}
      REMOVE citygml_function{}.codeSpace
      REMOVE citygml_usage{}
      REMOVE citygml_usage{}.codeSpace
      RENAME_SET_VALUE citygml_usage_0 > bldg_usage
      RENAME_SET_VALUE citygml_year_of_construction > bldg_yearOfConstruction
      RENAME_SET_VALUE citygml_year_of_demolition > bldg_yearOfDemolition
      RENAME_SET_VALUE citygml_roof_type > bldg_roofType
      REMOVE citygml_roof_type_codeSpace
      RENAME_SET_VALUE citygml_measured_height > bldg_measuredHeight
      REMOVE citygml_measured_height_units
      RENAME_SET_VALUE citygml_storeys_above_ground > bldg_storeysAboveGround
      RENAME_SET_VALUE citygml_storeys_below_ground > bldg_storeysBelowGround
      REMOVE citygml_storey_heights_above_ground
      REMOVE citygml_storey_heights_above_ground_units
      REMOVE citygml_storey_heights_below_ground
      REMOVE citygml_storey_heights_below_ground_units
      REMOVE citygml_outer_building_installation{}.xlink_href
      REMOVE citygml_interior_building_installation{}.xlink_href
      REMOVE citygml_bounded_by{}.xlink_href
      REMOVE citygml_level_of_detail{}
      REMOVE citygml_interior_room{}.xlink_href
      REMOVE citygml_consists_of_building_part{}.xlink_href
      REMOVE citygml_address{}.xlink_href
      RENAME_SET_VALUE Address > bldg_address
      REMOVE uro_building_details{}.uro_building_details_uro_serial_number_of_building_certification
      REMOVE uro_building_details{}.uro_building_details_uro_site_area
      REMOVE uro_building_details{}.uro_building_details_uro_site_area_units
      REMOVE uro_building_details{}.uro_building_details_uro_building_footprint_area
      REMOVE uro_building_details{}.uro_building_details_uro_building_footprint_area_units
      REMOVE uro_building_details{}.uro_building_details_uro_building_roof_edge_area
      REMOVE uro_building_details{}.uro_building_details_uro_building_roof_edge_area_units
      REMOVE uro_building_details{}.uro_building_details_uro_development_area
      REMOVE uro_building_details{}.uro_building_details_uro_development_area_units
      REMOVE uro_building_details{}.uro_building_details_uro_total_floor_area
      REMOVE uro_building_details{}.uro_building_details_uro_total_floor_area_units
      REMOVE uro_building_details{}.uro_building_details_uro_building_structure_type
      REMOVE uro_building_details{}.uro_building_details_uro_building_structure_type_codeSpace
      REMOVE uro_building_details{}.uro_building_details_uro_fireproof_structure_type
      REMOVE uro_building_details{}.uro_building_details_uro_fireproof_structure_type_codeSpace
      REMOVE uro_building_details{}.uro_building_details_uro_implementing_body
      REMOVE uro_building_details{}.uro_building_details_uro_urban_plan_type
      REMOVE uro_building_details{}.uro_building_details_uro_urban_plan_type_codeSpace
      REMOVE uro_building_details{}.uro_building_details_uro_districts_and_zones_type
      REMOVE uro_building_details{}.uro_building_details_uro_districts_and_zones_type_codeSpace
      REMOVE uro_building_details{}.uro_building_details_uro_land_use_plan_type
      REMOVE uro_building_details{}.uro_building_details_uro_area_classification_type
      REMOVE uro_building_details{}.uro_building_details_uro_area_classification_type_codeSpace
      REMOVE uro_building_details{}.uro_building_details_uro_land_use_plan_type_codeSpace
      REMOVE uro_building_details{}.uro_building_details_uro_prefecture
      REMOVE uro_building_details{}.uro_building_details_uro_prefecture_codeSpace
      REMOVE uro_building_details{}.uro_building_details_uro_city
      REMOVE uro_building_details{}.uro_building_details_uro_city_codeSpace
      REMOVE uro_building_details{}.uro_building_details_uro_reference
      REMOVE uro_building_details{}.uro_building_details_uro_note
      REMOVE uro_building_details{}.uro_building_details_uro_survey_year
      REMOVE uro_extended_attribute{}.uro_key_value_pair_uro_key
      REMOVE uro_extended_attribute{}.uro_key_value_pair_uro_key_codeSpace
      REMOVE uro_extended_attribute{}.uro_key_value_pair_uro_string_value
      REMOVE uro_extended_attribute{}.uro_key_value_pair_uro_int_value
      REMOVE uro_extended_attribute{}.uro_key_value_pair_uro_double_value
      REMOVE uro_extended_attribute{}.uro_key_value_pair_uro_code_value
      REMOVE uro_extended_attribute{}.uro_key_value_pair_uro_code_value_codeSpace
      REMOVE uro_extended_attribute{}.uro_key_value_pair_uro_measured_value
      REMOVE uro_extended_attribute{}.uro_key_value_pair_uro_measured_value_units
      REMOVE uro_extended_attribute{}.uro_key_value_pair_uro_date_value
      REMOVE uro_extended_attribute{}.uro_key_value_pair_uro_uri_value
      REMOVE uro_large_customer_facilities{}.uro_large_customer_facilities_uro_class
      REMOVE uro_large_customer_facilities{}.uro_large_customer_facilities_uro_class_codeSpace
      REMOVE uro_large_customer_facilities{}.uro_large_customer_facilities_uro_name
      REMOVE uro_large_customer_facilities{}.uro_large_customer_facilities_uro_capacity
      REMOVE uro_large_customer_facilities{}.uro_large_customer_facilities_uro_owner
      REMOVE uro_large_customer_facilities{}.uro_large_customer_facilities_uro_total_floor_area
      REMOVE uro_large_customer_facilities{}.uro_large_customer_facilities_uro_total_floor_area_units
      REMOVE uro_large_customer_facilities{}.uro_large_customer_facilities_uro_total_store_floor_area
      REMOVE uro_large_customer_facilities{}.uro_large_customer_facilities_uro_total_store_floor_area_units
      REMOVE uro_large_customer_facilities{}.uro_large_customer_facilities_uro_inaugural_date
      REMOVE uro_large_customer_facilities{}.uro_large_customer_facilities_uro_key_tenants
      REMOVE uro_large_customer_facilities{}.uro_large_customer_facilities_uro_availability
      REMOVE uro_large_customer_facilities{}.uro_large_customer_facilities_uro_urban_plan_type
      REMOVE uro_large_customer_facilities{}.uro_large_customer_facilities_uro_urban_plan_type_codeSpace
      REMOVE uro_large_customer_facilities{}.uro_large_customer_facilities_uro_districts_and_zones_type
      REMOVE uro_large_customer_facilities{}.uro_large_customer_facilities_uro_districts_and_zones_type_codeSpace
      REMOVE uro_large_customer_facilities{}.uro_large_customer_facilities_uro_land_use_plan_type
      REMOVE uro_large_customer_facilities{}.uro_large_customer_facilities_uro_land_use_plan_type_codeSpace
      REMOVE uro_large_customer_facilities{}.uro_large_customer_facilities_uro_area_classification_type
      REMOVE uro_large_customer_facilities{}.uro_large_customer_facilities_uro_area_classification_type_codeSpace
      REMOVE uro_large_customer_facilities{}.uro_large_customer_facilities_uro_prefecture
      REMOVE uro_large_customer_facilities{}.uro_large_customer_facilities_uro_prefecture_codeSpace
      REMOVE uro_large_customer_facilities{}.uro_large_customer_facilities_uro_city
      REMOVE uro_large_customer_facilities{}.uro_large_customer_facilities_uro_city_codeSpace
      REMOVE uro_large_customer_facilities{}.uro_large_customer_facilities_uro_reference
      REMOVE uro_large_customer_facilities{}.uro_large_customer_facilities_uro_note
      REMOVE uro_large_customer_facilities{}.uro_large_customer_facilities_uro_survey_year
      REMOVE citygml_fnction_0
      RENAME_SET_VALUE uro_building_details_uro_serial_number_of_building_certification_0 > uro_buildingDetails_serialNumberOfBuildingCertification
      RENAME_SET_VALUE uro_building_details_uro_site_area_0 > uro_buildingDetails_siteArea
      RENAME_SET_VALUE uro_building_details_uro_total_floor_area_0 > uro_buildingDetails_totalFloorArea
      RENAME_SET_VALUE uro_building_details_uro_building_footprint_area_0 > uro_buildingDetails_buildingFootprintArea
      RENAME_SET_VALUE uro_building_details_uro_building_roof_edge_area_0 > uro_buildingDetails_buildingRoofEdgeArea
      RENAME_SET_VALUE uro_building_details_uro_development_area_0 > uro_buildingDetails_developmentArea
      RENAME_SET_VALUE uro_building_details_uro_building_structure_type_0 > uro_buildingDetails_buildingStructureType
      RENAME_SET_VALUE uro_building_details_uro_fireproof_structure_type_0 > uro_buildingDetails_fireproofStructureType
      RENAME_SET_VALUE uro_building_details_uro_implementing_body_0 > uro_buildingDetails_implementingBody
      RENAME_SET_VALUE uro_building_details_uro_urban_plan_type_0 > uro_buildingDetails_urbanPlanType
      RENAME_SET_VALUE uro_building_details_uro_districts_and_zones_type_0 > uro_buildingDetails_districtsAndZonesType
      RENAME_SET_VALUE uro_building_details_uro_land_use_plan_type_0 > uro_buildingDetails_landUsePlanType
      RENAME_SET_VALUE uro_building_details_uro_area_classification_type_0 > uro_buildingDetails_areaClassificationType
      RENAME_SET_VALUE uro_building_details_uro_prefecture_0 > uro_buildingDetails_prefecture
      RENAME_SET_VALUE uro_building_details_uro_city_0 > uro_buildingDetails_city
      RENAME_SET_VALUE uro_building_details_uro_reference_0 > uro_buildingDetails_reference
      RENAME_SET_VALUE uro_building_details_uro_note_0 > uro_buildingDetails_note
      RENAME_SET_VALUE uro_building_details_uro_survey_year_0 > uro_buildingDetails_surveyYear
      RENAME_SET_VALUE uro_large_customer_facilities_uro_class_0 > uro_largeCustomerFacilities_class
      RENAME_SET_VALUE uro_large_customer_facilities_uro_name_0 > uro_largeCustomerFacilities_name
      RENAME_SET_VALUE uro_large_customer_facilities_uro_capacity_0 > uro_largeCustomerFacilities_capacity
      RENAME_SET_VALUE uro_large_customer_facilities_uro_owner_0 > uro_largeCustomerFacilities_owner
      RENAME_SET_VALUE uro_large_customer_facilities_uro_total_floor_area_0 > uro_largeCustomerFacilities_totalFloorArea
      RENAME_SET_VALUE uro_large_customer_facilities_uro_total_store_floor_area_0 > uro_largeCustomerFacilities_totalStoreFloorArea
      RENAME_SET_VALUE uro_large_customer_facilities_uro_inaugural_date_0 > uro_largeCustomerFacilities_inauguralDate
      RENAME_SET_VALUE uro_large_customer_facilities_uro_key_tenants_0 > uro_largeCustomerFacilities_keyTenants
      RENAME_SET_VALUE uro_large_customer_facilities_uro_availability_0 > uro_largeCustomerFacilities_availability
      RENAME_SET_VALUE uro_large_customer_facilities_uro_urban_plan_type_0 > uro_largeCustomerFacilities_urbanPlanType
      RENAME_SET_VALUE uro_large_customer_facilities_uro_districts_and_zones_type_0 > uro_largeCustomerFacilities_districtsAndZonesType
      RENAME_SET_VALUE uro_large_customer_facilities_uro_land_use_plan_type_0 > uro_largeCustomerFacilities_landUsePlanType
      RENAME_SET_VALUE uro_large_customer_facilities_uro_area_classification_type_0 > uro_largeCustomerFacilities_areaClassificationType
      RENAME_SET_VALUE uro_large_customer_facilities_uro_prefecture_0 > uro_largeCustomerFacilities_prefecture
      RENAME_SET_VALUE uro_large_customer_facilities_uro_city_0 > uro_largeCustomerFacilities_city
      RENAME_SET_VALUE uro_large_customer_facilities_uro_reference_0 > uro_largeCustomerFacilities_reference
      RENAME_SET_VALUE uro_large_customer_facilities_uro_note_0 > uro_largeCustomerFacilities_note
      RENAME_SET_VALUE uro_large_customer_facilities_uro_survey_year_0 > uro_largeCustomerFacilities_surveyYear
      REMOVE citygml_address
    -> FeatureJoiner_2 [LEFT]

Bookmark: 汎用属性 の XML 整形
text_line (reader TEXTLINE_1)
    attributes: text_line_data buffer
    -> Sampler
Sampler
    RATE = 1
    SAMPLE_MODE = No
    SAMPLE_TYPE_LONG = First N Features
    SAMPLED -> XMLTemplater [ROOT]
    SAMPLED -> XMLTemplater [SUB]
    NOT_SAMPLED -> XMLTemplater [SUB]
Note: XMLTemplaterで作成するXML / ---------- / <?xml version="1.0" encoding="UTF-16"?> / <Building gml_id="BLD_4ebdc535-945c-42f5-9363-49210a28c4d5"> / <attr name="平成28年度建物利用現況_図形面積" type="DOUBLE">306.99105</attr> / <attr name="荒川浸水想定区域_想定最大規模_浸水深" type="DOUBLE">0.29</attr> / <attr name="荒川浸水想定区域_想定最大規模_継続時間" type="DOUBLE">0</attr> / <attr name="平成28年度建物利用現況_建物地上階数" type="LONG">7</attr> / <attr name="平成28年度建物利用現況_建物地下階数" type="LONG">0</attr> / <attr name="平成28年度建物利用現況_建物構造コード" type="TEXT">11</attr> / <attr name="平成28年度建物利用現況_建物用途分類コード" type="TEXT">121</attr> / <attr name="平成28年度建物利用現況_建物用途細分類コード" type="TEXT">0</attr> / <attr name="平成28年度建物利用現況_延べ面積換算コード" type="TEXT">1</attr> / <attr name="平成28年度建物利用現況_延べ面積換算係数" type="TEXT">1</attr> / <attr name="平成28年度建物利用現況_区市町村コード" type="TEXT">103</attr> / <attr name="平成28年度建物利用現況_大字_町コード" type="TEXT">16</attr> / <attr name="平成28年度建物利用現況_町_丁目コード" type="TEXT">3</attr> / <attr name="平成28年度建物利用現況_13_区市町村コード_大字_町コード_町_丁目コード" type="TEXT">13103016003</attr> / <attr name="平成28年度建物利用現況_区市町村名称" type="TEXT">港区</attr> / <attr name="平成28年度建物利用現況_町丁目名称" type="TEXT">新橋三丁目</attr> / <attr name="荒川浸水想定区域_想定最大規模_規模" type="TEXT">L2</attr> / <attr name="荒川浸水想定区域_想定最大規模_浸水ランク" type="TEXT">1</attr> / </Building> / (中略) / </root>
XMLTemplater
    OUTPUT_XML_HEADER = Yes
    RESULT_ATTRIBUTE = _result
    ROOT_QUERY_EXPR:
      <root>{
          fme:process-features("SUB")
      }</root>
    SUB_QUERY_EXPR:
      declare namespace gml="http://www.opengis.net/gml";
      declare namespace gen="http://www.opengis.net/citygml/generics/2.0";
      declare namespace bldg="http://www.opengis.net/citygml/building/2.0";

      {
      let $doc := fme:get-xml-attribute("text_line_data")
      for $b in $doc//bldg:Building
      return
      <Building gml_id="{data($b/@gml:id)}">{
          for $genStrAttr in $b/gen:stringAttribute
          where $b/gen:stringAttribute
              let $tempgenstrname := "gen_"||{data($genStrAttr/@name)}
              let $genstrname := fn:translate($tempgenstrname, "・（(- 「」、。－+＋）)", "____________")
              let $genstrtype := "TEXT"
              return
              <attr name="{$genstrname}" type="{$genstrtype}">{data($genStrAttr/gen:value)}</attr>
          }{
          for $genIntAttr in $b/gen:intAttribute
          where $b/gen:intAttribute
              let $tempgenintname := "gen_"||{data($genIntAttr/@name)}
              let $genintname := fn:translate($tempgenintname, "・（(- 「」、。－+＋）)", "____________")
              let $geninttype := "LONG"
              return
              <attr name="{$genintname}" type="{$geninttype}">{data($genIntAttr/gen:value)}</attr>
          }{
          for $genDoubleAttr in $b/gen:doubleAttribute
          where $b/gen:doubleAttribute
              let $tempgendoublename := "gen_"||{data($genDoubleAttr/@name)}
              let $gendoublename := fn:translate($tempgendoublename, "・（(- 「」、。－+＋）)", "____________")
              let $gendoubletype := "DOUBLE"
              return
              <attr name="{$gendoublename}" type="{$gendoubletype}">{data($genDoubleAttr/gen:value)}</attr>
          }{
          for $genDateAttr in $b/gen:dateAttribute
          where $b/gen:dateAttribute
              let $tempgendatename := "gen_"||{data($genDateAttr/@name)}
              let $gendatename := fn:translate($tempgendatename, "・（(- 「」、。－+＋）)", "____________")
              let $gendatetype := "TEXT"
              return
              <attr name="{$gendatename}" type="{$gendatetype}">{data($genDateAttr/gen:value)}</attr>
          }{
          for $genUriAttr in $b/gen:uriAttribute
          where $b/gen:uriAttribute
              let $tempgenuriname := "gen_"||{data($genUriAttr/@name)}
              let $genuriname := fn:translate($tempgenuriname, "・（(- 「」、。－+＋）)", "____________")
              let $genuritype := "TEXT"
              return
              <attr name="{$genuriname}" type="{$genuritype}">{data($genUriAttr/gen:value)}</attr>
          }{
          for $genMeasureAttr in $b/gen:measureAttribute
          where $b/gen:measureAttribute
              let $tempgenmeasurename := "gen_"||{data($genMeasureAttr/@name)}
              let $genmeasurename := fn:translate($tempgenmeasurename, "・（(- 「」、。－+＋）)", "____________")
              let $genmeasuretype := "DOUBLE"
              return
              <attr name="{$genmeasurename}" type="{$genmeasuretype}">{data($genMeasureAttr/gen:value)}</attr>
          }{
          for $attrSet in $b/gen:genericAttributeSet
          where $attrSet/gen:measureAttribute
              for $measureAttr in $attrSet/gen:measureAttribute
              let $mtempname := "gen_"||{data($attrSet/@name)}||"_"||{data($measureAttr/@name)}
              let $mname := fn:translate($mtempname, "・（(- 「」、。－+＋）)", "____________")
              let $mtype := "DOUBLE"
              return
              <attr name="{$mname}" type="{$mtype}">{data($measureAttr/gen:value)}</attr>
          }{
          for $attrSet in $b/gen:genericAttributeSet
          where $attrSet/gen:intAttribute
              for $intAttr in $attrSet/gen:intAttribute
              let $itempname := "gen_"||{data($attrSet/@name)}||"_"||{data($intAttr/@name)}
              let $iname := fn:translate($itempname, "・（(- 「」、。－+＋）)", "____________")
              let $itype := "LONG"
              return
              <attr name="{$iname}" type="{$itype}">{data($intAttr/gen:value)}</attr>
          }{
          for $attrSet in $b/gen:genericAttributeSet
          where $attrSet/gen:stringAttribute
              for $stringAttr in $attrSet/gen:stringAttribute
              let $stempname := "gen_"||{data($attrSet/@name)}||"_"||{data($stringAttr/@name)}
              let $sname := fn:translate($stempname, "・（(- 「」、。－+＋）)", "____________")
              let $stype := "TEXT"
              return
              <attr name="{$sname}" type="{$stype}">{data($stringAttr/gen:value)}</attr>
          }{
          for $attrSet in $b/gen:genericAttributeSet
          where $attrSet/gen:doubleAttribute
              for $doubleAttr in $attrSet/gen:doubleAttribute
              let $dtempname := "gen_"||{data($attrSet/@name)}||"_"||{data($doubleAttr/@name)}
              let $dname := fn:translate($dtempname, "・（(- 「」、。－+＋）)", "____________")
              let $dtype := "DOUBLE"
              return
              <attr name="{$dname}" type="{$dtype}">{data($doubleAttr/gen:value)}</attr>
          }{
          for $attrSet in $b/gen:genericAttributeSet
          where $attrSet/gen:dateAttribute
              for $dateAttr in $attrSet/gen:dateAttribute
              let $datetempname := "gen_"||{data($attrSet/@name)}||"_"||{data($dateAttr/@name)}
              let $datename := fn:translate($datetempname, "・（(- 「」、。－+＋）)", "____________")
              let $datetype := "TEXT"
              return
              <attr name="{$datename}" type="{$datetype}">{data($dateAttr/gen:value)}</attr>
          }{
          for $attrSet in $b/gen:genericAttributeSet
          where $attrSet/gen:uriAttribute
              for $uriAttr in $attrSet/gen:uriAttribute
              let $utempname := "gen_"||{data($attrSet/@name)}||"_"||{data($uriAttr/@name)}
              let $uname := fn:translate($utempname, "・（(- 「」、。－+＋）)", "____________")
              let $utype := "TEXT"
              return
              <attr name="{$uname}" type="{$utype}">{data($uriAttr/gen:value)}</attr>
          }</Building>
      }
    VISIBLE_QUERY_VALIDATE = Yes
    -> TextDecoder
TextDecoder
    DEST_ATTR = _decoded
    ENCODING_TYPE = XML
    STRING_TO_DECODE = @Value(_result)
    -> XMLFormatter
XMLFormatter
    COLLAPSE_EMPTY_ELEMENT = No
    FORMATTING_CHOICE = Pretty-Print XML
    INDENT_SIZE = 1
    LIST_NAME = _xml_error
    NAMESPACE_CLEANUP = Yes
    OUTPUT_ENCODING = utf-8
    REMOVE_ALL_COMMENT = No
    REMOVE_EMPTY_ELEMENT = No
    REPLACE_TABS_WITH_SPACES = no
    SCHEMALOC_CLEANUP = No
    TEXT_INDENT = no
    WHITESPACE_HANDLING = Preserve all whitespace
    XML_ATTR_TEXT = _decoded
    XML_INPUT_TYPE = Attribute Specifying XML Text
    XML_OUTPUT_ATTR = _result
    XML_OUTPUT_TYPE = Attribute
    PASSED -> AttributeKeeper
AttributeKeeper
    KEEP_ATTRS = _result
    -> XMLFragmenter
Note: 建物ごとに、汎用属性のXMLを作成
XMLFragmenter
    ATTRIBUTE_XML = _result
    EMBEDDED_EXPRESSIONS = root/Building
    FEATURE_TYPES_FORMAT_NAME = XML
    MERGE_ATTRS = No
    REJECT_FEATURES_WITH_NO_FRAGMENTS = YES
    XML_SOURCE_TYPE = Attribute with XML document
    FRAGMENTS -> XMLXQueryExtractor_2
Note: Joinするときにキーとして使用する建物IDを属性として格納
XMLXQueryExtractor_2
    NEW_ATTRIBUTES = building_id
    QUERY_EXPR:
      declare namespace gml="http://www.opengis.net/gml";
      declare namespace gen="http://www.opengis.net/citygml/generics/2.0";
      declare namespace bldg="http://www.opengis.net/citygml/building/2.0";

      fme:set-attribute('building_id', data(/Building/@gml_id))
    RESULT_ATTRIBUTE = _result
    RESULT_TYPE_NAME = Separated values
    SEPARATOR_VALUE = ,
    WRITE_XML_HEADER = No
    XML_ATTR = xml_fragment
    XML_REMOVE_SOURCE_ATTR = No
    XML_TYPE = Attribute specifying XML
    XQUERY_TYPE = XQuery expression
    QUERY_RESULTS -> AttributeManager_2
AttributeManager_2
    ATTR_TABLE:
      RENAME_SET_VALUE xml_fragment > xml_genericAttributeSet
      REMOVE xml_id
      REMOVE xml_matched_element
      REMOVE xml_parent_id
      REMOVE xml_parent_child_pos
      REMOVE _result
    -> FeatureJoiner_2 [RIGHT]

Bookmark: 拡張属性への対応
lod0_Building (reader GEODATABASE_XML_1)
    attributes: OBJECTID integer, bldg_Building_gml_id char(50), gml_name char(50), bldg_class char(10), bldg_usage char(10), bldg_yearOfConstruction char(50), bldg_yearOfDemolition char(50), bldg_roofType char(10), bldg_measuredHeight double, bldg_storeysAboveGround integer, bldg_storeysBelowGround integer, uro_extendedAttribute_key2 char(10), uro_extendedAttribute_key3 char(10), uro_extendedAttribute_key4 char(10), uro_extendedAttribute_key5 char(10), uro_extendedAttribute_key6 char(10), uro_extendedAttribute_key7 char(10), uro_extendedAttribute_key8 char(10), uro_extendedAttribute_key9 char(10), uro_extendedAttribute_key10 char(10), uro_extendedAttribute_key100 char(10), uro_extendedAttribute_key101 char(10), uro_extendedAttribute_key102 char(10), uro_extendedAttribute_key103 char(10), uro_extendedAttribute_key104 char(10), uro_extendedAttribute_key105 char(10), uro_extendedAttribute_key106 char(10), uro_extendedAttribute_key107 char(10), uro_extendedAttribute_key108 char(10), uro_extendedAttribute_key109 char(10),
      uro_extendedAttribute_key110 char(10), uro_extendedAttribute_key111 char(10), uro_extendedAttribute_key112 char(10), uro_extendedAttribute_key113 char(10), uro_extendedAttribute_key114 char(10), uro_extendedAttribute_key115 char(10), uro_extendedAttribute_key116 char(10), uro_extendedAttribute_key117 char(10), uro_extendedAttribute_key118 char(10), uro_extendedAttribute_key119 char(10), uro_extendedAttribute_key120 char(10), bldg_address char(50), uro_buildingDetails_serialNumberOfBuildingCertification char(50), uro_buildingDetails_siteArea double, uro_buildingDetails_totalFloorArea double, uro_buildingDetails_buildingFootprintArea double, uro_buildingDetails_buildingRoofEdgeArea double, uro_buildingDetails_developmentArea double, uro_buildingDetails_buildingStructureType char(10), uro_buildingDetails_fireproofStructureType char(10), uro_buildingDetails_implementingBody char(50), uro_buildingDetails_urbanPlanType char(10), uro_buildingDetails_districtsAndZonesType char(10), uro_buildingDetails_landUsePlanType char(10), uro_buildingDetails_areaClassificationType char(10), uro_buildingDetails_prefecture char(2), uro_buildingDetails_city char(5), uro_buildingDetails_reference char(50), uro_buildingDetails_note char(50), uro_buildingDetails_surveyYear char(50),
      uro_largeCustomerFacilities_class char(10), uro_largeCustomerFacilities_name char(50), uro_largeCustomerFacilities_capacity integer, uro_largeCustomerFacilities_owner char(50), uro_largeCustomerFacilities_totalFloorArea double, uro_largeCustomerFacilities_totalStoreFloorArea double, uro_largeCustomerFacilities_inauguralDate char(50), uro_largeCustomerFacilities_keyTenants char(50), uro_largeCustomerFacilities_availability char(50), uro_largeCustomerFacilities_urbanPlanType char(10), uro_largeCustomerFacilities_districtsAndZonesType char(10), uro_largeCustomerFacilities_landUsePlanType char(10), uro_largeCustomerFacilities_areaClassificationType char(10), uro_largeCustomerFacilities_prefecture char(2), uro_largeCustomerFacilities_city char(5), uro_largeCustomerFacilities_reference char(50), uro_largeCustomerFacilities_note char(50), uro_largeCustomerFacilities_surveyYear char(50), xml_genericAttributeSet char(10000), Shape_Length double, Shape_Area double
    -> AttributeKeeper_2
AttributeKeeper_2
    KEEP_ATTRS = uro_extendedAttribute_key2,uro_extendedAttribute_key3,uro_extendedAttribute_key4,uro_extendedAttribute_key5,uro_extendedAttribute_key6,uro_extendedAttribute_key7,uro_extendedAttribute_key8,uro_extendedAttribute_key9,uro_extendedAttribute_key10,uro_extendedAttribute_key100,uro_extendedAttribute_key101,uro_extendedAttribute_key102,uro_extendedAttribute_key103,uro_extendedAttribute_key104,uro_extendedAttribute_key105,uro_extendedAttribute_key106,uro_extendedAttribute_key107,uro_extendedAttribute_key108,uro_extendedAttribute_key109,uro_extendedAttribute_key110,uro_extendedAttribute_key111,uro_extendedAttribute_key112,uro_extendedAttribute_key113,uro_extendedAttribute_key114,uro_extendedAttribute_key115,uro_extendedAttribute_key116,uro_extendedAttribute_key117,uro_extendedAttribute_key118,uro_extendedAttribute_key119,uro_extendedAttribute_key120
    -> AttributeManager_3
Building (reader XML_1)
    attributes: Building.id xml_char(41), address.Address.xalAddress.AddressDetails.Address xml_char(17), boundedBy{}.GroundSurface.id xml_char(41), boundedBy{}.GroundSurface.lod2MultiSurface.MultiSurface.surfaceMember.Polygon.exterior.LinearRing.id xml_char(19), boundedBy{}.GroundSurface.lod2MultiSurface.MultiSurface.surfaceMember.Polygon.exterior.LinearRing.posList xml_char(3100), boundedBy{}.GroundSurface.lod2MultiSurface.MultiSurface.surfaceMember.Polygon.id xml_char(19), boundedBy{}.GroundSurface.lod2MultiSurface.MultiSurface.surfaceMember.Polygon.interior.LinearRing.id xml_char(24), boundedBy{}.GroundSurface.lod2MultiSurface.MultiSurface.surfaceMember.Polygon.interior.LinearRing.posList xml_char(337), boundedBy{}.OuterCeilingSurface.id xml_char(24), boundedBy{}.OuterCeilingSurface.lod2MultiSurface.MultiSurface.surfaceMember.Polygon.exterior.LinearRing.id xml_char(24), boundedBy{}.OuterCeilingSurface.lod2MultiSurface.MultiSurface.surfaceMember.Polygon.exterior.LinearRing.posList xml_char(4062), boundedBy{}.OuterCeilingSurface.lod2MultiSurface.MultiSurface.surfaceMember.Polygon.id xml_char(24), boundedBy{}.RoofSurface.id xml_char(24), boundedBy{}.RoofSurface.lod2MultiSurface.MultiSurface.surfaceMember.Polygon.exterior.LinearRing.id xml_char(24), boundedBy{}.RoofSurface.lod2MultiSurface.MultiSurface.surfaceMember.Polygon.exterior.LinearRing.posList xml_char(4250), boundedBy{}.RoofSurface.lod2MultiSurface.MultiSurface.surfaceMember.Polygon.id xml_char(24), boundedBy{}.WallSurface.id xml_char(24), boundedBy{}.WallSurface.lod2MultiSurface.MultiSurface.surfaceMember.Polygon.exterior.LinearRing.id xml_char(24), boundedBy{}.WallSurface.lod2MultiSurface.MultiSurface.surfaceMember.Polygon.exterior.LinearRing.posList xml_char(6320), boundedBy{}.WallSurface.lod2MultiSurface.MultiSurface.surfaceMember.Polygon.id xml_char(24), buildingDetails.BuildingDetails.buildingRoofEdgeArea xml_decimal(10,5), buildingDetails.BuildingDetails.buildingRoofEdgeArea.uom xml_char(3), buildingDetails.BuildingDetails.city xml_decimal(6,0), buildingDetails.BuildingDetails.city.codeSpace xml_char(50), buildingDetails.BuildingDetails.districtsAndZonesType xml_decimal(3,0), buildingDetails.BuildingDetails.districtsAndZonesType.codeSpace xml_char(49), buildingDetails.BuildingDetails.fireproofStructureType xml_decimal(5,0), buildingDetails.BuildingDetails.fireproofStructureType.codeSpace xml_char(52), buildingDetails.BuildingDetails.landUsePlanType xml_decimal(5,0), buildingDetails.BuildingDetails.landUsePlanType.codeSpace xml_char(43),
      buildingDetails.BuildingDetails.prefecture xml_decimal(3,0), buildingDetails.BuildingDetails.prefecture.codeSpace xml_char(38), buildingDetails.BuildingDetails.surveyYear xml_decimal(5,0), extendedAttribute.KeyValuePair.codeValue xml_decimal(2,0), extendedAttribute.KeyValuePair.codeValue.codeSpace xml_char(43), extendedAttribute.KeyValuePair.key xml_decimal(2,0), extendedAttribute.KeyValuePair.key.codeSpace xml_char(42), extendedAttribute{}.KeyValuePair.codeValue xml_decimal(5,0), extendedAttribute{}.KeyValuePair.codeValue.codeSpace xml_char(43), extendedAttribute{}.KeyValuePair.key xml_decimal(2,0), extendedAttribute{}.KeyValuePair.key.codeSpace xml_char(42), genericAttributeSet.intAttribute{}.name xml_char(13), genericAttributeSet.intAttribute{}.value xml_decimal(3,0), genericAttributeSet.measureAttribute.name xml_char(9), genericAttributeSet.measureAttribute.value xml_decimal(10,5), genericAttributeSet.measureAttribute.value.uom xml_char(3), genericAttributeSet.name xml_char(37), genericAttributeSet.stringAttribute{}.name xml_char(48), genericAttributeSet.stringAttribute{}.value xml_char(12), genericAttributeSet{}.intAttribute{}.name xml_char(13), genericAttributeSet{}.intAttribute{}.value xml_decimal(3,0), genericAttributeSet{}.measureAttribute.name xml_char(9), genericAttributeSet{}.measureAttribute.value xml_decimal(10,5), genericAttributeSet{}.measureAttribute.value.uom xml_char(3), genericAttributeSet{}.name xml_char(37), genericAttributeSet{}.stringAttribute.name xml_char(11), genericAttributeSet{}.stringAttribute.value xml_decimal(2,0), genericAttributeSet{}.stringAttribute{}.name xml_char(48), genericAttributeSet{}.stringAttribute{}.value xml_char(17), lod0RoofEdge.MultiSurface.surfaceMember.Polygon.exterior.LinearRing.posList xml_char(4479),
      lod0RoofEdge.MultiSurface.surfaceMember.Polygon.interior.LinearRing.posList xml_char(1596), lod0RoofEdge.MultiSurface.surfaceMember.Polygon.interior{}.LinearRing.posList xml_char(276), lod1Solid.Solid.exterior.CompositeSurface.surfaceMember{}.Polygon.exterior.LinearRing.posList xml_char(3599), lod1Solid.Solid.exterior.CompositeSurface.surfaceMember{}.Polygon.interior.LinearRing.posList xml_char(1596), lod1Solid.Solid.exterior.CompositeSurface.surfaceMember{}.Polygon.interior{}.LinearRing.posList xml_char(216), lod2Solid.Solid.exterior.CompositeSurface.surfaceMember{} xml_char(1), lod2Solid.Solid.exterior.CompositeSurface.surfaceMember{}.href xml_char(25), measuredHeight xml_decimal(5,1), measuredHeight.uom xml_char(2), storeysAboveGround xml_decimal(3,0), storeysBelowGround xml_decimal(2,0), stringAttribute{}.name xml_char(33), stringAttribute{}.value xml_char(17), usage xml_decimal(5,0), usage.codeSpace xml_char(35), xml_fragment xml_xml, xml_id xml_char(21), xml_matched_element xml_char(9), xml_parent_child_pos xml_char(1), xml_parent_id xml_char(1)
    -> ListExploder
ListExploder
    ATTR_ACCUM_MODE = Merge List Attributes
    ATTR_CONFLICT_RES = Use List Attribute Values
    INDEX_ATTR = _element_index
    LIST_ATTR = extendedAttribute{}
    ELEMENTS -> AttributeKeeper_3
    <REJECTED> -> AttributeKeeper_3
AttributeKeeper_3
    KEEP_ATTRS = Building.id,KeyValuePair.codeValue,KeyValuePair.codeValue.codeSpace,KeyValuePair.key,KeyValuePair.key.codeSpace,extendedAttribute.KeyValuePair.codeValue,extendedAttribute.KeyValuePair.codeValue.codeSpace,extendedAttribute.KeyValuePair.key,extendedAttribute.KeyValuePair.key.codeSpace
    -> AttributeManager_3
AttributeManager_3
    ATTR_TABLE:
      SET_TO uro_extendedAttribute_key2 = FME_CONDITIONAL:DEFAULT_VALUE'FME_NULL_VALUE'BOOL_OP;OR;COMPOSITE_TEST;1 OR 2;TEST @Value(KeyValuePair.key) = 2;TEST @Value(extendedAttribute.KeyValuePair.key) = 2'@Value(extendedAttribute.KeyValuePair.codeValue)@Value(KeyValuePair.codeValue)'FME_NUM_CONDITIONS2___
      SET_TO uro_extendedAttribute_key3 = FME_CONDITIONAL:DEFAULT_VALUE'FME_NULL_VALUE'BOOL_OP;OR;COMPOSITE_TEST;1 OR 2;TEST @Value(KeyValuePair.key) = 3;TEST @Value(extendedAttribute.KeyValuePair.key) = 3'@Value(extendedAttribute.KeyValuePair.codeValue)@Value(KeyValuePair.codeValue)'FME_NUM_CONDITIONS2___
      SET_TO uro_extendedAttribute_key4 = FME_CONDITIONAL:DEFAULT_VALUE'FME_NULL_VALUE'BOOL_OP;OR;COMPOSITE_TEST;1 OR 2;TEST @Value(KeyValuePair.key) = 4;TEST @Value(extendedAttribute.KeyValuePair.key) = 4'@Value(extendedAttribute.KeyValuePair.codeValue)@Value(KeyValuePair.codeValue)'FME_NUM_CONDITIONS2___
      SET_TO uro_extendedAttribute_key5 = FME_CONDITIONAL:DEFAULT_VALUE'FME_NULL_VALUE'BOOL_OP;OR;COMPOSITE_TEST;1 OR 2;TEST @Value(KeyValuePair.key) = 5;TEST @Value(extendedAttribute.KeyValuePair.key) = 5'@Value(extendedAttribute.KeyValuePair.codeValue)@Value(KeyValuePair.codeValue)'FME_NUM_CONDITIONS2___
      SET_TO uro_extendedAttribute_key6 = FME_CONDITIONAL:DEFAULT_VALUE'FME_NULL_VALUE'BOOL_OP;OR;COMPOSITE_TEST;1 OR 2;TEST @Value(KeyValuePair.key) = 6;TEST @Value(extendedAttribute.KeyValuePair.key) = 6'@Value(extendedAttribute.KeyValuePair.codeValue)@Value(KeyValuePair.codeValue)'FME_NUM_CONDITIONS2___
      SET_TO uro_extendedAttribute_key7 = FME_CONDITIONAL:DEFAULT_VALUE'FME_NULL_VALUE'BOOL_OP;OR;COMPOSITE_TEST;1 OR 2;TEST @Value(KeyValuePair.key) = 7;TEST @Value(extendedAttribute.KeyValuePair.key) = 7'@Value(extendedAttribute.KeyValuePair.codeValue)@Value(KeyValuePair.codeValue)'FME_NUM_CONDITIONS2___
      SET_TO uro_extendedAttribute_key8 = FME_CONDITIONAL:DEFAULT_VALUE'FME_NULL_VALUE'BOOL_OP;OR;COMPOSITE_TEST;1 OR 2;TEST @Value(KeyValuePair.key) = 8;TEST @Value(extendedAttribute.KeyValuePair.key) = 8'@Value(extendedAttribute.KeyValuePair.codeValue)@Value(KeyValuePair.codeValue)'FME_NUM_CONDITIONS2___
      SET_TO uro_extendedAttribute_key9 = FME_CONDITIONAL:DEFAULT_VALUE'FME_NULL_VALUE'BOOL_OP;OR;COMPOSITE_TEST;1 OR 2;TEST @Value(KeyValuePair.key) = 9;TEST @Value(extendedAttribute.KeyValuePair.key) = 9'@Value(extendedAttribute.KeyValuePair.codeValue)@Value(KeyValuePair.codeValue)'FME_NUM_CONDITIONS2___
      SET_TO uro_extendedAttribute_key10 = FME_CONDITIONAL:DEFAULT_VALUE'FME_NULL_VALUE'BOOL_OP;OR;COMPOSITE_TEST;1 OR 2;TEST @Value(KeyValuePair.key) = 10;TEST @Value(extendedAttribute.KeyValuePair.key) = 10'@Value(extendedAttribute.KeyValuePair.codeValue)@Value(KeyValuePair.codeValue)'FME_NUM_CONDITIONS2___
      SET_TO uro_extendedAttribute_key100 = FME_CONDITIONAL:DEFAULT_VALUE'FME_NULL_VALUE'BOOL_OP;OR;COMPOSITE_TEST;1 OR 2;TEST @Value(KeyValuePair.key) = 100;TEST @Value(extendedAttribute.KeyValuePair.key) = 100'@Value(extendedAttribute.KeyValuePair.codeValue)@Value(KeyValuePair.codeValue)'FME_NUM_CONDITIONS2___
      SET_TO uro_extendedAttribute_key101 = FME_CONDITIONAL:DEFAULT_VALUE'FME_NULL_VALUE'BOOL_OP;OR;COMPOSITE_TEST;1 OR 2;TEST @Value(KeyValuePair.key) = 101;TEST @Value(extendedAttribute.KeyValuePair.key) = 101'@Value(extendedAttribute.KeyValuePair.codeValue)@Value(KeyValuePair.codeValue)'FME_NUM_CONDITIONS2___
      SET_TO uro_extendedAttribute_key102 = FME_CONDITIONAL:DEFAULT_VALUE'FME_NULL_VALUE'BOOL_OP;OR;COMPOSITE_TEST;1 OR 2;TEST @Value(KeyValuePair.key) = 102;TEST @Value(extendedAttribute.KeyValuePair.key) = 102'@Value(extendedAttribute.KeyValuePair.codeValue)@Value(KeyValuePair.codeValue)'FME_NUM_CONDITIONS2___
      SET_TO uro_extendedAttribute_key103 = FME_CONDITIONAL:DEFAULT_VALUE'FME_NULL_VALUE'BOOL_OP;OR;COMPOSITE_TEST;1 OR 2;TEST @Value(KeyValuePair.key) = 103;TEST @Value(extendedAttribute.KeyValuePair.key) = 103'@Value(extendedAttribute.KeyValuePair.codeValue)@Value(KeyValuePair.codeValue)'FME_NUM_CONDITIONS2___
      SET_TO uro_extendedAttribute_key104 = FME_CONDITIONAL:DEFAULT_VALUE'FME_NULL_VALUE'BOOL_OP;OR;COMPOSITE_TEST;1 OR 2;TEST @Value(KeyValuePair.key) = 104;TEST @Value(extendedAttribute.KeyValuePair.key) = 104'@Value(extendedAttribute.KeyValuePair.codeValue)@Value(KeyValuePair.codeValue)'FME_NUM_CONDITIONS2___
      SET_TO uro_extendedAttribute_key105 = FME_CONDITIONAL:DEFAULT_VALUE'FME_NULL_VALUE'BOOL_OP;OR;COMPOSITE_TEST;1 OR 2;TEST @Value(KeyValuePair.key) = 105;TEST @Value(extendedAttribute.KeyValuePair.key) = 105'@Value(extendedAttribute.KeyValuePair.codeValue)@Value(KeyValuePair.codeValue)'FME_NUM_CONDITIONS2___
      SET_TO uro_extendedAttribute_key106 = FME_CONDITIONAL:DEFAULT_VALUE'FME_NULL_VALUE'BOOL_OP;OR;COMPOSITE_TEST;1 OR 2;TEST @Value(KeyValuePair.key) = 106;TEST @Value(extendedAttribute.KeyValuePair.key) = 106'@Value(extendedAttribute.KeyValuePair.codeValue)@Value(KeyValuePair.codeValue)'FME_NUM_CONDITIONS2___
      SET_TO uro_extendedAttribute_key107 = FME_CONDITIONAL:DEFAULT_VALUE'FME_NULL_VALUE'BOOL_OP;OR;COMPOSITE_TEST;1 OR 2;TEST @Value(KeyValuePair.key) = 107;TEST @Value(extendedAttribute.KeyValuePair.key) = 107'@Value(extendedAttribute.KeyValuePair.codeValue)@Value(KeyValuePair.codeValue)'FME_NUM_CONDITIONS2___
      SET_TO uro_extendedAttribute_key108 = FME_CONDITIONAL:DEFAULT_VALUE'FME_NULL_VALUE'BOOL_OP;OR;COMPOSITE_TEST;1 OR 2;TEST @Value(KeyValuePair.key) = 108;TEST @Value(extendedAttribute.KeyValuePair.key) = 108'@Value(extendedAttribute.KeyValuePair.codeValue)@Value(KeyValuePair.codeValue)'FME_NUM_CONDITIONS2___
      SET_TO uro_extendedAttribute_key109 = FME_CONDITIONAL:DEFAULT_VALUE'FME_NULL_VALUE'BOOL_OP;OR;COMPOSITE_TEST;1 OR 2;TEST @Value(KeyValuePair.key) = 109;TEST @Value(extendedAttribute.KeyValuePair.key) = 109'@Value(extendedAttribute.KeyValuePair.codeValue)@Value(KeyValuePair.codeValue)'FME_NUM_CONDITIONS2___
      SET_TO uro_extendedAttribute_key110 = FME_CONDITIONAL:DEFAULT_VALUE'FME_NULL_VALUE'BOOL_OP;OR;COMPOSITE_TEST;1 OR 2;TEST @Value(KeyValuePair.key) = 110;TEST @Value(extendedAttribute.KeyValuePair.key) = 110'@Value(extendedAttribute.KeyValuePair.codeValue)@Value(KeyValuePair.codeValue)'FME_NUM_CONDITIONS2___
      SET_TO uro_extendedAttribute_key111 = FME_CONDITIONAL:DEFAULT_VALUE'FME_NULL_VALUE'BOOL_OP;OR;COMPOSITE_TEST;1 OR 2;TEST @Value(KeyValuePair.key) = 111;TEST @Value(extendedAttribute.KeyValuePair.key) = 111'@Value(extendedAttribute.KeyValuePair.codeValue)@Value(KeyValuePair.codeValue)'FME_NUM_CONDITIONS2___
      SET_TO uro_extendedAttribute_key112 = FME_CONDITIONAL:DEFAULT_VALUE'FME_NULL_VALUE'BOOL_OP;OR;COMPOSITE_TEST;1 OR 2;TEST @Value(KeyValuePair.key) = 112;TEST @Value(extendedAttribute.KeyValuePair.key) = 112'@Value(extendedAttribute.KeyValuePair.codeValue)@Value(KeyValuePair.codeValue)'FME_NUM_CONDITIONS2___
      SET_TO uro_extendedAttribute_key113 = FME_CONDITIONAL:DEFAULT_VALUE'FME_NULL_VALUE'BOOL_OP;OR;COMPOSITE_TEST;1 OR 2;TEST @Value(KeyValuePair.key) = 113;TEST @Value(extendedAttribute.KeyValuePair.key) = 113'@Value(extendedAttribute.KeyValuePair.codeValue)@Value(KeyValuePair.codeValue)'FME_NUM_CONDITIONS2___
      SET_TO uro_extendedAttribute_key114 = FME_CONDITIONAL:DEFAULT_VALUE'FME_NULL_VALUE'BOOL_OP;OR;COMPOSITE_TEST;1 OR 2;TEST @Value(KeyValuePair.key) = 114;TEST @Value(extendedAttribute.KeyValuePair.key) = 114'@Value(extendedAttribute.KeyValuePair.codeValue)@Value(KeyValuePair.codeValue)'FME_NUM_CONDITIONS2___
      SET_TO uro_extendedAttribute_key115 = FME_CONDITIONAL:DEFAULT_VALUE'FME_NULL_VALUE'BOOL_OP;OR;COMPOSITE_TEST;1 OR 2;TEST @Value(KeyValuePair.key) = 115;TEST @Value(extendedAttribute.KeyValuePair.key) = 115'@Value(extendedAttribute.KeyValuePair.codeValue)@Value(KeyValuePair.codeValue)'FME_NUM_CONDITIONS2___
      SET_TO uro_extendedAttribute_key116 = FME_CONDITIONAL:DEFAULT_VALUE'FME_NULL_VALUE'BOOL_OP;OR;COMPOSITE_TEST;1 OR 2;TEST @Value(KeyValuePair.key) = 116;TEST @Value(extendedAttribute.KeyValuePair.key) = 116'@Value(extendedAttribute.KeyValuePair.codeValue)@Value(KeyValuePair.codeValue)'FME_NUM_CONDITIONS2___
      SET_TO uro_extendedAttribute_key117 = FME_CONDITIONAL:DEFAULT_VALUE'FME_NULL_VALUE'BOOL_OP;OR;COMPOSITE_TEST;1 OR 2;TEST @Value(KeyValuePair.key) = 117;TEST @Value(extendedAttribute.KeyValuePair.key) = 117'@Value(extendedAttribute.KeyValuePair.codeValue)@Value(KeyValuePair.codeValue)'FME_NUM_CONDITIONS2___
      SET_TO uro_extendedAttribute_key118 = FME_CONDITIONAL:DEFAULT_VALUE'FME_NULL_VALUE'BOOL_OP;OR;COMPOSITE_TEST;1 OR 2;TEST @Value(KeyValuePair.key) = 118;TEST @Value(extendedAttribute.KeyValuePair.key) = 118'@Value(extendedAttribute.KeyValuePair.codeValue)@Value(KeyValuePair.codeValue)'FME_NUM_CONDITIONS2___
      SET_TO uro_extendedAttribute_key119 = FME_CONDITIONAL:DEFAULT_VALUE'FME_NULL_VALUE'BOOL_OP;OR;COMPOSITE_TEST;1 OR 2;TEST @Value(KeyValuePair.key) = 119;TEST @Value(extendedAttribute.KeyValuePair.key) = 119'@Value(extendedAttribute.KeyValuePair.codeValue)@Value(KeyValuePair.codeValue)'FME_NUM_CONDITIONS2___
      SET_TO uro_extendedAttribute_key120 = FME_CONDITIONAL:DEFAULT_VALUE'FME_NULL_VALUE'BOOL_OP;OR;COMPOSITE_TEST;1 OR 2;TEST @Value(KeyValuePair.key) = 120;TEST @Value(extendedAttribute.KeyValuePair.key) = 120'@Value(extendedAttribute.KeyValuePair.codeValue)@Value(KeyValuePair.codeValue)'FME_NUM_CONDITIONS2___
    -> Aggregator
Aggregator
    ACCUM_ATTRS_NAME = Merge Incoming Attributes
    CONCAT_ATTRS = uro_extendedAttribute_key2 uro_extendedAttribute_key3 uro_extendedAttribute_key10 uro_extendedAttribute_key4 uro_extendedAttribute_key5 uro_extendedAttribute_key6 uro_extendedAttribute_key7 uro_extendedAttribute_key8 uro_extendedAttribute_key9 uro_extendedAttribute_key100 uro_extendedAttribute_key101 uro_extendedAttribute_key102 uro_extendedAttribute_key103 uro_extendedAttribute_key104 uro_extendedAttribute_key105 uro_extendedAttribute_key106 uro_extendedAttribute_key107 uro_extendedAttribute_key108 uro_extendedAttribute_key109 uro_extendedAttribute_key110 uro_extendedAttribute_key111 uro_extendedAttribute_key112 uro_extendedAttribute_key113 uro_extendedAttribute_key114 uro_extendedAttribute_key115 uro_extendedAttribute_key116 uro_extendedAttribute_key117 uro_extendedAttribute_key118 uro_extendedAttribute_key119 uro_extendedAttribute_key120
    GROUP_BY = Building.id
    MODE = Attributes Only
    AGGREGATE -> AttributeKeeper_4
AttributeKeeper_4
    KEEP_ATTRS = Building.id,uro_extendedAttribute_key2,uro_extendedAttribute_key3,uro_extendedAttribute_key10,uro_extendedAttribute_key4,uro_extendedAttribute_key5,uro_extendedAttribute_key6,uro_extendedAttribute_key7,uro_extendedAttribute_key8,uro_extendedAttribute_key9,uro_extendedAttribute_key100,uro_extendedAttribute_key101,uro_extendedAttribute_key102,uro_extendedAttribute_key103,uro_extendedAttribute_key104,uro_extendedAttribute_key105,uro_extendedAttribute_key106,uro_extendedAttribute_key107,uro_extendedAttribute_key108,uro_extendedAttribute_key109,uro_extendedAttribute_key110,uro_extendedAttribute_key111,uro_extendedAttribute_key112,uro_extendedAttribute_key113,uro_extendedAttribute_key114,uro_extendedAttribute_key115,uro_extendedAttribute_key116,uro_extendedAttribute_key117,uro_extendedAttribute_key118,uro_extendedAttribute_key119,uro_extendedAttribute_key120
    -> FeatureJoiner_3 [RIGHT]
    -> FeatureJoiner_5 [RIGHT]

Bookmark: 拡張属性を結合
FeatureJoiner_5
    ATTR_CONFLICT_RES = Use Left
    GEOMETRY_HANDLING = Use Left
    JOIN_KEYS = bldg_Building_gml_id Building.id STRING
    JOIN_MODE = Inner
    JOINED -> TestFilter_2
FeatureJoiner_3
    ATTR_CONFLICT_RES = Use Left
    GEOMETRY_HANDLING = Use Left
    JOIN_KEYS = bldg_Building_gml_id Building.id STRING
    JOIN_MODE = Inner
    JOINED -> TestFilter
