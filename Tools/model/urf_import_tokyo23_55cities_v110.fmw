FME workspace urf_import_tokyo23_55cities_v110.fmw

Parameters:
- SourceDataset_CITYGML =   # Input CityGML File(s)
- TEMPLATEFILE_GEODATABASE_FILE =   # Template XML Workspace Document (Schema Only)
- DestDataset_GEODATABASE_FILE =   # Output File Geodatabase

Readers:
- CITYGML_1: CITYGML from $(SourceDataset_CITYGML)

Writers:
- GEODATABASE_FILE_1: GEODATABASE_FILE to $(DestDataset_GEODATABASE_FILE)

Note: CityGML Reader Parameters / GML SRS Axis Order: 2,1,3
AttributeManager_3
    ATTR_TABLE:
      RENAME_SET_VALUE gml_id > urf_DistrictAndZones_gml_id
      REMOVE gml_parent_id
      REMOVE citygml_target_uri
      REMOVE citygml_feature_role
      REMOVE citygml_feature_role_attr_name
      REMOVE citygml_feature_role_attr_val
      REMOVE gml_description
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE urf_class_codeSpace
      REMOVE urf_function{}
      REMOVE urf_function{}.codeSpace
      RENAME_SET_VALUE urf_enactment_date > urf_enactmentDate
      REMOVE urf_enactment_fiscal_year
      REMOVE urf_expiration_date
      REMOVE urf_expiration_fiscal_year
      REMOVE urf_legal_grounds_urf_legal_grounds_urf_name_of_regulation
      REMOVE urf_legal_grounds_urf_legal_grounds_urf_name_of_regulation_codeSpace
      REMOVE urf_legal_grounds_urf_legal_grounds_urf_articles_of_regulation
      REMOVE urf_legal_grounds_urf_legal_grounds_urf_articles_of_regulation_codeSpace
      REMOVE urf_legal_grounds_urf_legal_grounds_urf_date
      RENAME_SET_VALUE urf_nominal_area > urf_nominalArea
      REMOVE urf_nominal_area_units
      REMOVE urf_abstract
      REMOVE urf_validity
      REMOVE urf_urban_plan_type_codeSpace
      RENAME_SET_VALUE urf_area_classification_type > urf_areaClassificationType
      REMOVE urf_area_classification_type_codeSpace
      REMOVE urf_prefecture_codeSpace
      REMOVE urf_city_codeSpace
      REMOVE urf_note
      RENAME_SET_VALUE urf_survey_year > urf_surveyYear
      REMOVE citygml_level_of_detail{}
      REMOVE urf_target{}.xlink_href
      RENAME_SET_VALUE urf_final_publication_date > urf_finalPublicationDate
      RENAME_SET_VALUE urf_area_applied > urf_appliedArea
    -> GeometryPartExtractor_3
GeometryPartExtractor_3
    GQUERY:
      for $geom in //geometry
      where $geom/parent::geometry/@fme_geometry_type = 'IFMEFace'
      return number($geom/@fme_id)
    EXTRACTED -> lod0_DistrictAndZones (writer GEODATABASE_FILE_1)
AttributeManager_2
    ATTR_TABLE:
      RENAME_SET_VALUE gml_id > urf_AreaClassification_gml_id
      REMOVE gml_parent_id
      REMOVE citygml_target_uri
      REMOVE citygml_feature_role
      REMOVE citygml_feature_role_attr_name
      REMOVE citygml_feature_role_attr_val
      REMOVE gml_description
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE urf_class_codeSpace
      REMOVE urf_function{}
      REMOVE urf_function{}.codeSpace
      RENAME_SET_VALUE urf_enactment_date > urf_enactmentDate
      REMOVE urf_enactment_fiscal_year
      REMOVE urf_expiration_date
      REMOVE urf_expiration_fiscal_year
      REMOVE urf_legal_grounds_urf_legal_grounds_urf_name_of_regulation
      REMOVE urf_legal_grounds_urf_legal_grounds_urf_name_of_regulation_codeSpace
      REMOVE urf_legal_grounds_urf_legal_grounds_urf_articles_of_regulation
      REMOVE urf_legal_grounds_urf_legal_grounds_urf_articles_of_regulation_codeSpace
      REMOVE urf_legal_grounds_urf_legal_grounds_urf_date
      RENAME_SET_VALUE urf_nominal_area > urf_nominalArea
      REMOVE urf_nominal_area_units
      REMOVE urf_abstract
      REMOVE urf_validity
      REMOVE urf_urban_plan_type_codeSpace
      REMOVE urf_area_classification_type
      REMOVE urf_area_classification_type_codeSpace
      REMOVE urf_prefecture_codeSpace
      REMOVE urf_city_codeSpace
      REMOVE urf_note
      RENAME_SET_VALUE urf_survey_year > urf_surveyYear
      REMOVE citygml_level_of_detail{}
      REMOVE urf_target{}.xlink_href
      RENAME_SET_VALUE urf_final_publication_date > urf_finalPublicationDate
      RENAME_SET_VALUE urf_area_applied > urf_appliedArea
    -> GeometryPartExtractor_2
GeometryPartExtractor_2
    GQUERY:
      for $geom in //geometry
      where $geom/parent::geometry/@fme_geometry_type = 'IFMEFace'
      return number($geom/@fme_id)
    EXTRACTED -> lod0_AreaClassification (writer GEODATABASE_FILE_1)
AttributeManager
    ATTR_TABLE:
      RENAME_SET_VALUE gml_id > urf_UrbanPlan_gml_id
      REMOVE gml_parent_id
      REMOVE citygml_target_uri
      REMOVE citygml_feature_role
      REMOVE citygml_feature_role_attr_name
      REMOVE citygml_feature_role_attr_val
      REMOVE gml_description
      REMOVE citygml_creationDate
      REMOVE citygml_terminationDate
      REMOVE externalReference{}.externalObject.name
      REMOVE externalReference{}.externalObject.uri
      REMOVE externalReference{}.informationSystem
      REMOVE citygml_generalizes_to{}.xlink_href
      REMOVE citygml_relative_to_terrain
      REMOVE citygml_relative_to_water
      REMOVE urf_class_codeSpace
      REMOVE urf_function{}
      REMOVE urf_function{}.codeSpace
      RENAME_SET_VALUE urf_enactment_date > urf_enactmentDate
      REMOVE urf_enactment_fiscal_year
      REMOVE urf_expiration_date
      REMOVE urf_expiration_fiscal_year
      REMOVE urf_legal_grounds_urf_legal_grounds_urf_name_of_regulation
      REMOVE urf_legal_grounds_urf_legal_grounds_urf_name_of_regulation_codeSpace
      REMOVE urf_legal_grounds_urf_legal_grounds_urf_articles_of_regulation
      REMOVE urf_legal_grounds_urf_legal_grounds_urf_articles_of_regulation_codeSpace
      REMOVE urf_legal_grounds_urf_legal_grounds_urf_date
      RENAME_SET_VALUE urf_nominal_area > urf_nominalArea
      REMOVE urf_nominal_area_units
      REMOVE urf_abstract
      REMOVE urf_validity
      REMOVE urf_urban_plan_type
      REMOVE urf_urban_plan_type_codeSpace
      REMOVE urf_area_classification_type
      REMOVE urf_area_classification_type_codeSpace
      REMOVE urf_prefecture_codeSpace
      REMOVE urf_city_codeSpace
      REMOVE urf_note
      RENAME_SET_VALUE urf_survey_year > urf_surveyYear
      REMOVE citygml_level_of_detail{}
      REMOVE urf_target{}.xlink_href
      RENAME_SET_VALUE urf_final_publication_date > urf_finalPublicationDate
      RENAME_SET_VALUE urf_area_applied > urf_appliedArea
    -> GeometryPartExtractor
GeometryPartExtractor
    GQUERY:
      for $geom in //geometry
      where $geom/parent::geometry/@fme_geometry_type = 'IFMEFace'
      return number($geom/@fme_id)
    EXTRACTED -> lod0_UrbanPlan (writer GEODATABASE_FILE_1)

Bookmark: CityGML Feature Types
CityModel (reader CITYGML_1)
    attributes: citygml_target_uri xml_buffer, gml_description xml_buffer, gml_name xml_buffer, citygml_city_object_member{}.xlink_href xml_buffer, gml_feature_member{}.xlink_href xml_buffer
DistrictsAndZones (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), urf_class xml_buffer, urf_class_codeSpace xml_buffer, urf_function{} xml_buffer, urf_function{}.codeSpace xml_buffer, urf_enactment_date xml_date, urf_enactment_fiscal_year xml_buffer, urf_expiration_date xml_date, urf_expiration_fiscal_year xml_buffer, urf_legal_grounds_urf_legal_grounds_urf_name_of_regulation xml_buffer, urf_legal_grounds_urf_legal_grounds_urf_name_of_regulation_codeSpace xml_buffer, urf_legal_grounds_urf_legal_grounds_urf_articles_of_regulation xml_buffer, urf_legal_grounds_urf_legal_grounds_urf_articles_of_regulation_codeSpace xml_buffer, urf_legal_grounds_urf_legal_grounds_urf_date xml_date, urf_custodian xml_buffer, urf_nominal_area xml_real64, urf_nominal_area_units xml_buffer,
      urf_abstract xml_buffer, urf_validity xml_boolean, urf_urban_plan_type xml_buffer, urf_urban_plan_type_codeSpace xml_buffer, urf_area_classification_type xml_buffer, urf_area_classification_type_codeSpace xml_buffer, urf_prefecture xml_buffer, urf_prefecture_codeSpace xml_buffer, urf_city xml_buffer, urf_city_codeSpace xml_buffer, urf_reference xml_buffer, urf_note xml_buffer, urf_survey_year xml_buffer, citygml_level_of_detail{} xml_buffer, urf_target{}.xlink_href xml_buffer, urf_final_publication_date xml_date, urf_area_applied xml_buffer
    -> AttributeManager_3
AreaClassification (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), urf_class xml_buffer, urf_class_codeSpace xml_buffer, urf_function{} xml_buffer, urf_function{}.codeSpace xml_buffer, urf_enactment_date xml_date, urf_enactment_fiscal_year xml_buffer, urf_expiration_date xml_date, urf_expiration_fiscal_year xml_buffer, urf_legal_grounds_urf_legal_grounds_urf_name_of_regulation xml_buffer, urf_legal_grounds_urf_legal_grounds_urf_name_of_regulation_codeSpace xml_buffer, urf_legal_grounds_urf_legal_grounds_urf_articles_of_regulation xml_buffer, urf_legal_grounds_urf_legal_grounds_urf_articles_of_regulation_codeSpace xml_buffer, urf_legal_grounds_urf_legal_grounds_urf_date xml_date, urf_custodian xml_buffer, urf_nominal_area xml_real64, urf_nominal_area_units xml_buffer,
      urf_abstract xml_buffer, urf_validity xml_boolean, urf_urban_plan_type xml_buffer, urf_urban_plan_type_codeSpace xml_buffer, urf_area_classification_type xml_buffer, urf_area_classification_type_codeSpace xml_buffer, urf_prefecture xml_buffer, urf_prefecture_codeSpace xml_buffer, urf_city xml_buffer, urf_city_codeSpace xml_buffer, urf_reference xml_buffer, urf_note xml_buffer, urf_survey_year xml_buffer, citygml_level_of_detail{} xml_buffer, urf_target{}.xlink_href xml_buffer, urf_final_publication_date xml_date, urf_area_applied xml_buffer
    -> AttributeManager_2
UrbanPlan (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), urf_class xml_buffer, urf_class_codeSpace xml_buffer, urf_function{} xml_buffer, urf_function{}.codeSpace xml_buffer, urf_enactment_date xml_date, urf_enactment_fiscal_year xml_buffer, urf_expiration_date xml_date, urf_expiration_fiscal_year xml_buffer, urf_legal_grounds_urf_legal_grounds_urf_name_of_regulation xml_buffer, urf_legal_grounds_urf_legal_grounds_urf_name_of_regulation_codeSpace xml_buffer, urf_legal_grounds_urf_legal_grounds_urf_articles_of_regulation xml_buffer, urf_legal_grounds_urf_legal_grounds_urf_articles_of_regulation_codeSpace xml_buffer, urf_legal_grounds_urf_legal_grounds_urf_date xml_date, urf_custodian xml_buffer, urf_nominal_area xml_real64, urf_nominal_area_units xml_buffer,
      urf_abstract xml_buffer, urf_validity xml_boolean, urf_urban_plan_type xml_buffer, urf_urban_plan_type_codeSpace xml_buffer, urf_area_classification_type xml_buffer, urf_area_classification_type_codeSpace xml_buffer, urf_prefecture xml_buffer, urf_prefecture_codeSpace xml_buffer, urf_city xml_buffer, urf_city_codeSpace xml_buffer, urf_reference xml_buffer, urf_note xml_buffer, urf_survey_year xml_buffer, citygml_level_of_detail{} xml_buffer, urf_target{}.xlink_href xml_buffer, urf_final_publication_date xml_date, urf_area_applied xml_buffer
    -> AttributeManager

Bookmark: GDBに書込み(XMLスキーマを指定)
lod0_DistrictAndZones (writer GEODATABASE_FILE_1)
    attributes: urf_DistrictAndZones_gml_id char(50), gml_name char(50), urf_class char(10), urf_enactmentDate char(50), urf_custodian char(50), urf_nominalArea double, urf_urban_plan_type char(10), urf_areaClassificationType char(10), urf_prefecture char(2), urf_city char(5), urf_reference char(50), urf_surveyYear char(50), urf_finalPublicationDate char(50), urf_appliedArea char(50)
lod0_AreaClassification (writer GEODATABASE_FILE_1)
    attributes: urf_AreaClassification_gml_id char(50), gml_name char(50), urf_class char(10), urf_enactmentDate char(50), urf_custodian char(50), urf_nominalArea double, urf_urban_plan_type char(10), urf_prefecture char(2), urf_city char(5), urf_reference char(50), urf_surveyYear char(50), urf_finalPublicationDate char(50), urf_appliedArea char(50)
lod0_UrbanPlan (writer GEODATABASE_FILE_1)
    attributes: urf_UrbanPlan_gml_id char(50), gml_name char(50), urf_class char(10), urf_enactmentDate char(50), urf_custodian char(50), urf_nominalArea double, urf_prefecture char(2), urf_city char(5), urf_reference char(50), urf_surveyYear char(50), urf_finalPublicationDate char(50), urf_appliedArea char(50)
